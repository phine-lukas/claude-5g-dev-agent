-- ASN.1 extracted from TS 38.413, all -- ASN1START / -- ASN1STOP blocks,
-- in document order. Generated by scripts/ensure_specs.py; do not edit.

-- **************************************************************
--
-- Elementary Procedure definitions
--
-- **************************************************************
NGAP-PDU-Descriptions {
itu-t (0) identified-organization (4) etsi (0) mobileDomain (0)
ngran-Access (22) modules (3) ngap (1) version1 (1) ngap-PDU-Descriptions (0)}
DEFINITIONS AUTOMATIC TAGS ::=
BEGIN
-- **************************************************************
--
-- IE parameter types from other modules.
--
-- **************************************************************
IMPORTS
Criticality,
ProcedureCode
FROM NGAP-CommonDataTypes
AMFConfigurationUpdate,
AMFConfigurationUpdateAcknowledge,
AMFConfigurationUpdateFailure,
AMFStatusIndication,
CellTrafficTrace,
DeactivateTrace,
DownlinkNASTransport,
DownlinkNonUEAssociatedNRPPaTransport,
DownlinkRANConfigurationTransfer,
DownlinkRANStatusTransfer,
DownlinkUEAssociatedNRPPaTransport,
ErrorIndication,
HandoverCancel,
HandoverCancelAcknowledge,
HandoverCommand,
HandoverFailure,
HandoverNotify,
HandoverPreparationFailure,
HandoverRequest,
HandoverRequestAcknowledge,
HandoverRequired,
InitialContextSetupFailure,
InitialContextSetupRequest,
InitialContextSetupResponse,
InitialUEMessage,
LocationReport,
LocationReportingControl,
LocationReportingFailureIndication,
NASNonDeliveryIndication,
NGReset,
NGResetAcknowledge,
NGSetupFailure,
NGSetupRequest,
NGSetupResponse,
OverloadStart,
OverloadStop,
Paging,
PathSwitchRequest,
PathSwitchRequestAcknowledge,
PathSwitchRequestFailure,
PDUSessionResourceModifyConfirm,
PDUSessionResourceModifyIndication,
PDUSessionResourceModifyRequest,
PDUSessionResourceModifyResponse,
PDUSessionResourceNotify,
PDUSessionResourceReleaseCommand,
PDUSessionResourceReleaseResponse,
PDUSessionResourceSetupRequest,
PDUSessionResourceSetupResponse,
PrivateMessage,
PWSCancelRequest,
PWSCancelResponse,
PWSFailureIndication,
PWSRestartIndication,
RANConfigurationUpdate,
RANConfigurationUpdateAcknowledge,
RANConfigurationUpdateFailure,
RerouteNASRequest,
RRCInactiveTransitionReport,
SecondaryRATDataUsageReport,
TraceFailureIndication,
TraceStart,
UEContextModificationFailure,
UEContextModificationRequest,
UEContextModificationResponse,
UEContextReleaseCommand,
UEContextReleaseComplete,
UEContextReleaseRequest,
UERadioCapabilityCheckRequest,
UERadioCapabilityCheckResponse,
UERadioCapabilityInfoIndication,
UETNLABindingReleaseRequest,
UplinkNASTransport,
UplinkNonUEAssociatedNRPPaTransport,
UplinkRANConfigurationTransfer,
UplinkRANStatusTransfer,
UplinkUEAssociatedNRPPaTransport,
WriteReplaceWarningRequest,
WriteReplaceWarningResponse
FROM NGAP-PDU-Contents
id-AMFConfigurationUpdate,
id-AMFStatusIndication,
id-CellTrafficTrace,
id-DeactivateTrace,
id-DownlinkNASTransport,
id-DownlinkNonUEAssociatedNRPPaTransport,
id-DownlinkRANConfigurationTransfer,
id-DownlinkRANStatusTransfer,
id-DownlinkUEAssociatedNRPPaTransport,
id-ErrorIndication,
id-HandoverCancel,
id-HandoverNotification,
id-HandoverPreparation,
id-HandoverResourceAllocation,
id-InitialContextSetup,
id-InitialUEMessage,
id-LocationReport,
id-LocationReportingControl,
id-LocationReportingFailureIndication,
id-NASNonDeliveryIndication,
id-NGReset,
id-NGSetup,
id-OverloadStart,
id-OverloadStop,
id-Paging,
id-PathSwitchRequest,
id-PDUSessionResourceModify,
id-PDUSessionResourceModifyIndication,
id-PDUSessionResourceNotify,
id-PDUSessionResourceRelease,
id-PDUSessionResourceSetup,
id-PrivateMessage,
id-PWSCancel,
id-PWSFailureIndication,
id-PWSRestartIndication,
id-RANConfigurationUpdate,
id-RerouteNASRequest,
id-RRCInactiveTransitionReport,
id-SecondaryRATDataUsageReport,
id-TraceFailureIndication,
id-TraceStart,
id-UEContextModification,
id-UEContextRelease,
id-UEContextReleaseRequest,
id-UERadioCapabilityCheck,
id-UERadioCapabilityInfoIndication,
id-UETNLABindingRelease,
id-UplinkNASTransport,
id-UplinkNonUEAssociatedNRPPaTransport,
id-UplinkRANConfigurationTransfer,
id-UplinkRANStatusTransfer,
id-UplinkUEAssociatedNRPPaTransport,
id-WriteReplaceWarning
FROM NGAP-Constants;
-- **************************************************************
--
-- Interface Elementary Procedure Class
--
-- **************************************************************
NGAP-ELEMENTARY-PROCEDURE ::= CLASS {
&InitiatingMessage ,
&SuccessfulOutcome OPTIONAL,
&UnsuccessfulOutcome OPTIONAL,
&procedureCode ProcedureCode UNIQUE,
&criticality Criticality DEFAULT ignore
}
WITH SYNTAX {
INITIATING MESSAGE &InitiatingMessage
[SUCCESSFUL OUTCOME &SuccessfulOutcome]
[UNSUCCESSFUL OUTCOME &UnsuccessfulOutcome]
PROCEDURE CODE &procedureCode
[CRITICALITY &criticality]
}
-- **************************************************************
--
-- Interface PDU Definition
--
-- **************************************************************
NGAP-PDU ::= CHOICE {
initiatingMessage InitiatingMessage,
successfulOutcome SuccessfulOutcome,
unsuccessfulOutcome UnsuccessfulOutcome,
...
}
InitiatingMessage ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&InitiatingMessage ({NGAP-ELEMENTARY-PROCEDURES}{@procedureCode})
}
SuccessfulOutcome ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&SuccessfulOutcome ({NGAP-ELEMENTARY-PROCEDURES}{@procedureCode})
}
UnsuccessfulOutcome ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&UnsuccessfulOutcome ({NGAP-ELEMENTARY-PROCEDURES}{@procedureCode})
}
-- **************************************************************
--
-- Interface Elementary Procedure List
--
-- **************************************************************
NGAP-ELEMENTARY-PROCEDURES NGAP-ELEMENTARY-PROCEDURE ::= {
NGAP-ELEMENTARY-PROCEDURES-CLASS-1 |
NGAP-ELEMENTARY-PROCEDURES-CLASS-2,
...
}
NGAP-ELEMENTARY-PROCEDURES-CLASS-1 NGAP-ELEMENTARY-PROCEDURE ::= {
aMFConfigurationUpdate |
handoverCancel |
handoverPreparation |
handoverResourceAllocation |
initialContextSetup |
nGReset |
nGSetup |
pathSwitchRequest |
pDUSessionResourceModify |
pDUSessionResourceModifyIndication |
pDUSessionResourceRelease |
pDUSessionResourceSetup |
pWSCancel |
rANConfigurationUpdate |
uEContextModification |
uEContextRelease |
uERadioCapabilityCheck |
writeReplaceWarning
}
NGAP-ELEMENTARY-PROCEDURES-CLASS-2 NGAP-ELEMENTARY-PROCEDURE ::= {
aMFStatusIndication |
cellTrafficTrace |
deactivateTrace |
downlinkNASTransport |
downlinkNonUEAssociatedNRPPaTransport |
downlinkRANConfigurationTransfer |
downlinkRANStatusTransfer |
downlinkUEAssociatedNRPPaTransport |
errorIndication |
handoverNotification |
initialUEMessage |
locationReport |
locationReportingControl |
locationReportingFailureIndication |
nASNonDeliveryIndication |
overloadStart |
overloadStop |
paging |
pDUSessionResourceNotify |
privateMessage |
pWSFailureIndication |
pWSRestartIndication |
rerouteNASRequest |
rRCInactiveTransitionReport |
secondaryRATDataUsageReport |
traceFailureIndication |
traceStart |
uEContextReleaseRequest |
uERadioCapabilityInfoIndication |
uETNLABindingRelease |
uplinkNASTransport |
uplinkNonUEAssociatedNRPPaTransport |
uplinkRANConfigurationTransfer |
uplinkRANStatusTransfer |
uplinkUEAssociatedNRPPaTransport
}
-- **************************************************************
--
-- Interface Elementary Procedures
--
-- **************************************************************
aMFConfigurationUpdate NGAP-ELEMENTARY-PROCEDURE ::= {
INITIATING MESSAGE AMFConfigurationUpdate
SUCCESSFUL OUTCOME AMFConfigurationUpdateAcknowledge
UNSUCCESSFUL OUTCOME AMFConfigurationUpdateFailure
PROCEDURE CODE id-AMFConfigurationUpdate
CRITICALITY reject
}
aMFStatusIndication NGAP-ELEMENTARY-PROCEDURE ::={
INITIATING MESSAGE AMFStatusIndication
PROCEDURE CODE id-AMFStatusIndication
CRITICALITY ignore
}
cellTrafficTrace NGAP-ELEMENTARY-PROCEDURE ::={
INITIATING MESSAGE CellTrafficTrace
PROCEDURE CODE id-CellTrafficTrace
CRITICALITY ignore
}
deactivateTrace NGAP-ELEMENTARY-PROCEDURE ::= {
INITIATING MESSAGE DeactivateTrace
PROCEDURE CODE id-DeactivateTrace
CRITICALITY ignore
}
downlinkNASTransport NGAP-ELEMENTARY-PROCEDURE ::= {
INITIATING MESSAGE DownlinkNASTransport
PROCEDURE CODE id-DownlinkNASTransport
CRITICALITY ignore
}
downlinkNonUEAssociatedNRPPaTransport NGAP-ELEMENTARY-PROCEDURE ::= {
INITIATING MESSAGE DownlinkNonUEAssociatedNRPPaTransport
PROCEDURE CODE id-DownlinkNonUEAssociatedNRPPaTransport
CRITICALITY ignore
}
downlinkRANConfigurationTransfer NGAP-ELEMENTARY-PROCEDURE ::= {
INITIATING MESSAGE DownlinkRANConfigurationTransfer
PROCEDURE CODE id-DownlinkRANConfigurationTransfer
CRITICALITY ignore
}
downlinkRANStatusTransfer NGAP-ELEMENTARY-PROCEDURE ::= {
INITIATING MESSAGE DownlinkRANStatusTransfer
PROCEDURE CODE id-DownlinkRANStatusTransfer
CRITICALITY ignore
}
downlinkUEAssociatedNRPPaTransport NGAP-ELEMENTARY-PROCEDURE ::= {
INITIATING MESSAGE DownlinkUEAssociatedNRPPaTransport
PROCEDURE CODE id-DownlinkUEAssociatedNRPPaTransport
CRITICALITY ignore
}
errorIndication NGAP-ELEMENTARY-PROCEDURE ::= {
INITIATING MESSAGE ErrorIndication
PROCEDURE CODE id-ErrorIndication
CRITICALITY ignore
}
handoverCancel NGAP-ELEMENTARY-PROCEDURE ::= {
INITIATING MESSAGE HandoverCancel
SUCCESSFUL OUTCOME HandoverCancelAcknowledge
PROCEDURE CODE id-HandoverCancel
CRITICALITY reject
}
handoverNotification NGAP-ELEMENTARY-PROCEDURE ::= {
INITIATING MESSAGE HandoverNotify
PROCEDURE CODE id-HandoverNotification
CRITICALITY ignore
}
handoverPreparation NGAP-ELEMENTARY-PROCEDURE ::= {
INITIATING MESSAGE HandoverRequired
SUCCESSFUL OUTCOME HandoverCommand
UNSUCCESSFUL OUTCOME HandoverPreparationFailure
PROCEDURE CODE id-HandoverPreparation
CRITICALITY reject
}
handoverResourceAllocation NGAP-ELEMENTARY-PROCEDURE ::= {
INITIATING MESSAGE HandoverRequest
SUCCESSFUL OUTCOME HandoverRequestAcknowledge
UNSUCCESSFUL OUTCOME HandoverFailure
PROCEDURE CODE id-HandoverResourceAllocation
CRITICALITY reject
}
initialContextSetup NGAP-ELEMENTARY-PROCEDURE ::= {
INITIATING MESSAGE InitialContextSetupRequest
SUCCESSFUL OUTCOME InitialContextSetupResponse
UNSUCCESSFUL OUTCOME InitialContextSetupFailure
PROCEDURE CODE id-InitialContextSetup
CRITICALITY reject
}
initialUEMessage NGAP-ELEMENTARY-PROCEDURE ::= {
INITIATING MESSAGE InitialUEMessage
PROCEDURE CODE id-InitialUEMessage
CRITICALITY ignore
}
locationReport NGAP-ELEMENTARY-PROCEDURE ::= {
INITIATING MESSAGE LocationReport
PROCEDURE CODE id-LocationReport
CRITICALITY ignore
}
locationReportingControl NGAP-ELEMENTARY-PROCEDURE ::= {
INITIATING MESSAGE LocationReportingControl
PROCEDURE CODE id-LocationReportingControl
CRITICALITY ignore
}
locationReportingFailureIndication NGAP-ELEMENTARY-PROCEDURE ::= {
INITIATING MESSAGE LocationReportingFailureIndication
PROCEDURE CODE id-LocationReportingFailureIndication
CRITICALITY ignore
}
nASNonDeliveryIndication NGAP-ELEMENTARY-PROCEDURE ::= {
INITIATING MESSAGE NASNonDeliveryIndication
PROCEDURE CODE id-NASNonDeliveryIndication
CRITICALITY ignore
}
nGReset NGAP-ELEMENTARY-PROCEDURE ::= {
INITIATING MESSAGE NGReset
SUCCESSFUL OUTCOME NGResetAcknowledge
PROCEDURE CODE id-NGReset
CRITICALITY reject
}
nGSetup NGAP-ELEMENTARY-PROCEDURE ::= {
INITIATING MESSAGE NGSetupRequest
SUCCESSFUL OUTCOME NGSetupResponse
UNSUCCESSFUL OUTCOME NGSetupFailure
PROCEDURE CODE id-NGSetup
CRITICALITY reject
}
overloadStart NGAP-ELEMENTARY-PROCEDURE ::= {
INITIATING MESSAGE OverloadStart
PROCEDURE CODE id-OverloadStart
CRITICALITY ignore
}
overloadStop NGAP-ELEMENTARY-PROCEDURE ::= {
INITIATING MESSAGE OverloadStop
PROCEDURE CODE id-OverloadStop
CRITICALITY reject
}
paging NGAP-ELEMENTARY-PROCEDURE ::= {
INITIATING MESSAGE Paging
PROCEDURE CODE id-Paging
CRITICALITY ignore
}
pathSwitchRequest NGAP-ELEMENTARY-PROCEDURE ::= {
INITIATING MESSAGE PathSwitchRequest
SUCCESSFUL OUTCOME PathSwitchRequestAcknowledge
UNSUCCESSFUL OUTCOME PathSwitchRequestFailure
PROCEDURE CODE id-PathSwitchRequest
CRITICALITY reject
}
pDUSessionResourceModify NGAP-ELEMENTARY-PROCEDURE ::= {
INITIATING MESSAGE PDUSessionResourceModifyRequest
SUCCESSFUL OUTCOME PDUSessionResourceModifyResponse
PROCEDURE CODE id-PDUSessionResourceModify
CRITICALITY reject
}
pDUSessionResourceModifyIndication NGAP-ELEMENTARY-PROCEDURE ::= {
INITIATING MESSAGE PDUSessionResourceModifyIndication
SUCCESSFUL OUTCOME PDUSessionResourceModifyConfirm
PROCEDURE CODE id-PDUSessionResourceModifyIndication
CRITICALITY reject
}
pDUSessionResourceNotify NGAP-ELEMENTARY-PROCEDURE ::= {
INITIATING MESSAGE PDUSessionResourceNotify
PROCEDURE CODE id-PDUSessionResourceNotify
CRITICALITY ignore
}
pDUSessionResourceRelease NGAP-ELEMENTARY-PROCEDURE ::= {
INITIATING MESSAGE PDUSessionResourceReleaseCommand
SUCCESSFUL OUTCOME PDUSessionResourceReleaseResponse
PROCEDURE CODE id-PDUSessionResourceRelease
CRITICALITY reject
}
pDUSessionResourceSetup NGAP-ELEMENTARY-PROCEDURE ::= {
INITIATING MESSAGE PDUSessionResourceSetupRequest
SUCCESSFUL OUTCOME PDUSessionResourceSetupResponse
PROCEDURE CODE id-PDUSessionResourceSetup
CRITICALITY reject
}
privateMessage NGAP-ELEMENTARY-PROCEDURE ::= {
INITIATING MESSAGE PrivateMessage
PROCEDURE CODE id-PrivateMessage
CRITICALITY ignore
}
pWSCancel NGAP-ELEMENTARY-PROCEDURE ::= {
INITIATING MESSAGE PWSCancelRequest
SUCCESSFUL OUTCOME PWSCancelResponse
PROCEDURE CODE id-PWSCancel
CRITICALITY reject
}
pWSFailureIndication NGAP-ELEMENTARY-PROCEDURE ::= {
INITIATING MESSAGE PWSFailureIndication
PROCEDURE CODE id-PWSFailureIndication
CRITICALITY ignore
}
pWSRestartIndication NGAP-ELEMENTARY-PROCEDURE ::= {
INITIATING MESSAGE PWSRestartIndication
PROCEDURE CODE id-PWSRestartIndication
CRITICALITY ignore
}
rANConfigurationUpdate NGAP-ELEMENTARY-PROCEDURE ::= {
INITIATING MESSAGE RANConfigurationUpdate
SUCCESSFUL OUTCOME RANConfigurationUpdateAcknowledge
UNSUCCESSFUL OUTCOME RANConfigurationUpdateFailure
PROCEDURE CODE id-RANConfigurationUpdate
CRITICALITY reject
}
rerouteNASRequest NGAP-ELEMENTARY-PROCEDURE ::= {
INITIATING MESSAGE RerouteNASRequest
PROCEDURE CODE id-RerouteNASRequest
CRITICALITY reject
}
rRCInactiveTransitionReport NGAP-ELEMENTARY-PROCEDURE ::= {
INITIATING MESSAGE RRCInactiveTransitionReport
PROCEDURE CODE id-RRCInactiveTransitionReport
CRITICALITY ignore
}
secondaryRATDataUsageReport NGAP-ELEMENTARY-PROCEDURE ::= {
INITIATING MESSAGE SecondaryRATDataUsageReport
PROCEDURE CODE id-SecondaryRATDataUsageReport
CRITICALITY ignore
}
traceFailureIndication NGAP-ELEMENTARY-PROCEDURE ::= {
INITIATING MESSAGE TraceFailureIndication
PROCEDURE CODE id-TraceFailureIndication
CRITICALITY ignore
}
traceStart NGAP-ELEMENTARY-PROCEDURE ::= {
INITIATING MESSAGE TraceStart
PROCEDURE CODE id-TraceStart
CRITICALITY ignore
}
uEContextModification NGAP-ELEMENTARY-PROCEDURE ::= {
INITIATING MESSAGE UEContextModificationRequest
SUCCESSFUL OUTCOME UEContextModificationResponse
UNSUCCESSFUL OUTCOME UEContextModificationFailure
PROCEDURE CODE id-UEContextModification
CRITICALITY reject
}
uEContextRelease NGAP-ELEMENTARY-PROCEDURE ::= {
INITIATING MESSAGE UEContextReleaseCommand
SUCCESSFUL OUTCOME UEContextReleaseComplete
PROCEDURE CODE id-UEContextRelease
CRITICALITY reject
}
uEContextReleaseRequest NGAP-ELEMENTARY-PROCEDURE ::= {
INITIATING MESSAGE UEContextReleaseRequest
PROCEDURE CODE id-UEContextReleaseRequest
CRITICALITY ignore
}
uERadioCapabilityCheck NGAP-ELEMENTARY-PROCEDURE ::= {
INITIATING MESSAGE UERadioCapabilityCheckRequest
SUCCESSFUL OUTCOME UERadioCapabilityCheckResponse
PROCEDURE CODE id-UERadioCapabilityCheck
CRITICALITY reject
}
uERadioCapabilityInfoIndication NGAP-ELEMENTARY-PROCEDURE ::= {
INITIATING MESSAGE UERadioCapabilityInfoIndication
PROCEDURE CODE id-UERadioCapabilityInfoIndication
CRITICALITY ignore
}
uETNLABindingRelease NGAP-ELEMENTARY-PROCEDURE ::= {
INITIATING MESSAGE UETNLABindingReleaseRequest
PROCEDURE CODE id-UETNLABindingRelease
CRITICALITY ignore
}
uplinkNASTransport NGAP-ELEMENTARY-PROCEDURE ::= {
INITIATING MESSAGE UplinkNASTransport
PROCEDURE CODE id-UplinkNASTransport
CRITICALITY ignore
}
uplinkNonUEAssociatedNRPPaTransport NGAP-ELEMENTARY-PROCEDURE ::= {
INITIATING MESSAGE UplinkNonUEAssociatedNRPPaTransport
PROCEDURE CODE id-UplinkNonUEAssociatedNRPPaTransport
CRITICALITY ignore
}
uplinkRANConfigurationTransfer NGAP-ELEMENTARY-PROCEDURE ::= {
INITIATING MESSAGE UplinkRANConfigurationTransfer
PROCEDURE CODE id-UplinkRANConfigurationTransfer
CRITICALITY ignore
}
uplinkRANStatusTransfer NGAP-ELEMENTARY-PROCEDURE ::= {
INITIATING MESSAGE UplinkRANStatusTransfer
PROCEDURE CODE id-UplinkRANStatusTransfer
CRITICALITY ignore
}
uplinkUEAssociatedNRPPaTransport NGAP-ELEMENTARY-PROCEDURE ::= {
INITIATING MESSAGE UplinkUEAssociatedNRPPaTransport
PROCEDURE CODE id-UplinkUEAssociatedNRPPaTransport
CRITICALITY ignore
}
writeReplaceWarning NGAP-ELEMENTARY-PROCEDURE ::= {
INITIATING MESSAGE WriteReplaceWarningRequest
SUCCESSFUL OUTCOME WriteReplaceWarningResponse
PROCEDURE CODE id-WriteReplaceWarning
CRITICALITY reject
}
END

-- **************************************************************
--
-- PDU definitions for NGAP.
--
-- **************************************************************
NGAP-PDU-Contents {
itu-t (0) identified-organization (4) etsi (0) mobileDomain (0)
ngran-Access (22) modules (3) ngap (1) version1 (1) ngap-PDU-Contents (1) }
DEFINITIONS AUTOMATIC TAGS ::=
BEGIN
-- **************************************************************
--
-- IE parameter types from other modules.
--
-- **************************************************************
IMPORTS
AllowedNSSAI,
AMFName,
AMFSetID,
AMF-TNLAssociationSetupList,
AMF-TNLAssociationToAddList,
AMF-TNLAssociationToRemoveList,
AMF-TNLAssociationToUpdateList,
AMF-UE-NGAP-ID,
AssistanceDataForPaging,
BroadcastCancelledAreaList,
BroadcastCompletedAreaList,
CancelAllWarningMessages,
Cause,
CellIDListForRestart,
CNAssistedRANTuning,
ConcurrentWarningMessageInd,
CoreNetworkAssistanceInformationForInactive,
CPTransportLayerInformation,
CriticalityDiagnostics,
DataCodingScheme,
DirectForwardingPathAvailability,
EmergencyAreaIDListForRestart,
EmergencyFallbackIndicator,
EN-DCSONConfigurationTransfer,
EUTRA-CGI,
FiveG-S-TMSI,
GlobalRANNodeID,
GUAMI,
HandoverFlag,
HandoverType,
IMSVoiceSupportIndicator,
IndexToRFSP,
InfoOnRecommendedCellsAndRANNodesForPaging,
LocationReportingRequestType,
MaskedIMEISV,
MessageIdentifier,
MobilityRestrictionList,
NAS-PDU,
NASSecurityParametersFromNGRAN,
NewSecurityContextInd,
NGRAN-CGI,
NGRAN-TNLAssociationToRemoveList,
NGRANTraceID,
NR-CGI,
NRPPa-PDU,
NumberOfBroadcastsRequested,
OverloadResponse,
OverloadStartNSSAIList,
PagingDRX,
PagingOrigin,
PagingPriority,
PDUSessionAggregateMaximumBitRate,
PDUSessionResourceAdmittedList,
PDUSessionResourceFailedToModifyListModCfm,
PDUSessionResourceFailedToModifyListModRes,
PDUSessionResourceFailedToSetupListCxtFail,
PDUSessionResourceFailedToSetupListCxtRes,
PDUSessionResourceFailedToSetupListHOAck,
PDUSessionResourceFailedToSetupListPSReq,
PDUSessionResourceFailedToSetupListSURes,
PDUSessionResourceHandoverList,
PDUSessionResourceListCxtRelCpl,
PDUSessionResourceListCxtRelReq,
PDUSessionResourceListHORqd,
PDUSessionResourceModifyListModCfm,
PDUSessionResourceModifyListModInd,
PDUSessionResourceModifyListModReq,
PDUSessionResourceModifyListModRes,
PDUSessionResourceNotifyList,
PDUSessionResourceReleasedListNot,
PDUSessionResourceReleasedListPSAck,
PDUSessionResourceReleasedListPSFail,
PDUSessionResourceReleasedListRelRes,
PDUSessionResourceSecondaryRATUsageList,
PDUSessionResourceSetupListCxtReq,
PDUSessionResourceSetupListCxtRes,
PDUSessionResourceSetupListHOReq,
PDUSessionResourceSetupListSUReq,
PDUSessionResourceSetupListSURes,
PDUSessionResourceSwitchedList,
PDUSessionResourceToBeSwitchedDLList,
PDUSessionResourceToReleaseListHOCmd,
PDUSessionResourceToReleaseListRelCmd,
PLMNIdentity,
PLMNSupportList,
PWSFailedCellIDList,
RANNodeName,
RANPagingPriority,
RANStatusTransfer-TransparentContainer,
RAN-UE-NGAP-ID,
RedirectionVoiceFallback,
RelativeAMFCapacity,
RepetitionPeriod,
ResetType,
RoutingID,
RRCEstablishmentCause,
RRCInactiveTransitionReportRequest,
RRCState,
SecurityContext,
SecurityKey,
SerialNumber,
ServedGUAMIList,
SliceSupportList,
S-NSSAI,
SONConfigurationTransfer,
SourceToTarget-TransparentContainer,
SourceToTarget-AMFInformationReroute,
SupportedTAList,
TAIListForPaging,
TAIListForRestart,
TargetID,
TargetToSource-TransparentContainer,
TimeToWait,
TNLAssociationList,
TraceActivation,
TrafficLoadReductionIndication,
TransportLayerAddress,
UEAggregateMaximumBitRate,
UE-associatedLogicalNG-connectionList,
UEContextRequest,
UE-NGAP-IDs,
UEPagingIdentity,
UEPresenceInAreaOfInterestList,
UERadioCapability,
UERadioCapabilityForPaging,
UERetentionInformation,
UESecurityCapabilities,
UnavailableGUAMIList,
UserLocationInformation,
WarningAreaCoordinates,
WarningAreaList,
WarningMessageContents,
WarningSecurityInfo,
WarningType
FROM NGAP-IEs
PrivateIE-Container{},
ProtocolExtensionContainer{},
ProtocolIE-Container{},
ProtocolIE-ContainerList{},
ProtocolIE-ContainerPair{},
ProtocolIE-SingleContainer{},
NGAP-PRIVATE-IES,
NGAP-PROTOCOL-EXTENSION,
NGAP-PROTOCOL-IES,
NGAP-PROTOCOL-IES-PAIR
FROM NGAP-Containers
id-AllowedNSSAI,
id-AMFName,
id-AMFOverloadResponse,
id-AMFSetID,
id-AMF-TNLAssociationFailedToSetupList,
id-AMF-TNLAssociationSetupList,
id-AMF-TNLAssociationToAddList,
id-AMF-TNLAssociationToRemoveList,
id-AMF-TNLAssociationToUpdateList,
id-AMFTrafficLoadReductionIndication,
id-AMF-UE-NGAP-ID,
id-AssistanceDataForPaging,
id-BroadcastCancelledAreaList,
id-BroadcastCompletedAreaList,
id-CancelAllWarningMessages,
id-Cause,
id-CellIDListForRestart,
id-CNAssistedRANTuning,
id-ConcurrentWarningMessageInd,
id-CoreNetworkAssistanceInformationForInactive,
id-CriticalityDiagnostics,
id-DataCodingScheme,
id-DefaultPagingDRX,
id-DirectForwardingPathAvailability,
id-EmergencyAreaIDListForRestart,
id-EmergencyFallbackIndicator,
id-ENDC-SONConfigurationTransferDL,
id-ENDC-SONConfigurationTransferUL,
id-EUTRA-CGI,
id-FiveG-S-TMSI,
id-GlobalRANNodeID,
id-GUAMI,
id-HandoverFlag,
id-HandoverType,
id-IMSVoiceSupportIndicator,
id-IndexToRFSP,
id-InfoOnRecommendedCellsAndRANNodesForPaging,
id-LocationReportingRequestType,
id-MaskedIMEISV,
id-MessageIdentifier,
id-MobilityRestrictionList,
id-NAS-PDU,
id-NASC,
id-NASSecurityParametersFromNGRAN,
id-NewAMF-UE-NGAP-ID,
id-NewGUAMI,
id-NewSecurityContextInd,
id-NGAP-Message,
id-NGRAN-CGI,
id-NGRAN-TNLAssociationToRemoveList,
id-NGRANTraceID,
id-NR-CGI,
id-NRPPa-PDU,
id-NumberOfBroadcastsRequested,
id-OldAMF,
id-OverloadStartNSSAIList,
id-PagingDRX,
id-PagingOrigin,
id-PagingPriority,
id-PDUSessionResourceAdmittedList,
id-PDUSessionResourceFailedToModifyListModCfm,
id-PDUSessionResourceFailedToModifyListModRes,
id-PDUSessionResourceFailedToSetupListCxtFail,
id-PDUSessionResourceFailedToSetupListCxtRes,
id-PDUSessionResourceFailedToSetupListHOAck,
id-PDUSessionResourceFailedToSetupListPSReq,
id-PDUSessionResourceFailedToSetupListSURes,
id-PDUSessionResourceHandoverList,
id-PDUSessionResourceListCxtRelCpl,
id-PDUSessionResourceListCxtRelReq,
id-PDUSessionResourceListHORqd,
id-PDUSessionResourceModifyListModCfm,
id-PDUSessionResourceModifyListModInd,
id-PDUSessionResourceModifyListModReq,
id-PDUSessionResourceModifyListModRes,
id-PDUSessionResourceNotifyList,
id-PDUSessionResourceReleasedListNot,
id-PDUSessionResourceReleasedListPSAck,
id-PDUSessionResourceReleasedListPSFail,
id-PDUSessionResourceReleasedListRelRes,
id-PDUSessionResourceSecondaryRATUsageList,
id-PDUSessionResourceSetupListCxtReq,
id-PDUSessionResourceSetupListCxtRes,
id-PDUSessionResourceSetupListHOReq,
id-PDUSessionResourceSetupListSUReq,
id-PDUSessionResourceSetupListSURes,
id-PDUSessionResourceSwitchedList,
id-PDUSessionResourceToBeSwitchedDLList,
id-PDUSessionResourceToReleaseListHOCmd,
id-PDUSessionResourceToReleaseListRelCmd,
id-PLMNSupportList,
id-PWSFailedCellIDList,
id-RANNodeName,
id-RANPagingPriority,
id-RANStatusTransfer-TransparentContainer,
id-RAN-UE-NGAP-ID,
id-RedirectionVoiceFallback,
id-RelativeAMFCapacity,
id-RepetitionPeriod,
id-ResetType,
id-RoutingID,
id-RRCEstablishmentCause,
id-RRCInactiveTransitionReportRequest,
id-RRCState,
id-SecurityContext,
id-SecurityKey,
id-SelectedPLMNIdentity,
id-SerialNumber,
id-ServedGUAMIList,
id-SliceSupportList,
id-SONConfigurationTransferDL,
id-SONConfigurationTransferUL,
id-SourceAMF-UE-NGAP-ID,
id-SourceToTarget-TransparentContainer,
id-SourceToTarget-AMFInformationReroute,
id-SupportedTAList,
id-TAIListForPaging,
id-TAIListForRestart,
id-TargetID,
id-TargetToSource-TransparentContainer,
id-TimeToWait,
id-TraceActivation,
id-TraceCollectionEntityIPAddress,
id-UEAggregateMaximumBitRate,
id-UE-associatedLogicalNG-connectionList,
id-UEContextRequest,
id-UE-NGAP-IDs,
id-UEPagingIdentity,
id-UEPresenceInAreaOfInterestList,
id-UERadioCapability,
id-UERadioCapabilityForPaging,
id-UERetentionInformation,
id-UESecurityCapabilities,
id-UnavailableGUAMIList,
id-UserLocationInformation,
id-WarningAreaCoordinates,
id-WarningAreaList,
id-WarningMessageContents,
id-WarningSecurityInfo,
id-WarningType
FROM NGAP-Constants;
-- **************************************************************
--
-- PDU SESSION MANAGEMENT ELEMENTARY PROCEDURES
--
-- **************************************************************
-- **************************************************************
--
-- PDU Session Resource Setup Elementary Procedure
--
-- **************************************************************
-- **************************************************************
--
-- PDU SESSION RESOURCE SETUP REQUEST
--
-- **************************************************************
PDUSessionResourceSetupRequest ::= SEQUENCE {
protocolIEs ProtocolIE-Container { {PDUSessionResourceSetupRequestIEs} },
...
}
PDUSessionResourceSetupRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-NAS-PDU CRITICALITY reject TYPE NAS-PDU PRESENCE optional }|
{ ID id-PDUSessionResourceSetupListSUReq CRITICALITY reject TYPE PDUSessionResourceSetupListSUReq PRESENCE mandatory }|
{ ID id-UEAggregateMaximumBitRate CRITICALITY ignore TYPE UEAggregateMaximumBitRate PRESENCE optional },
...
}
-- **************************************************************
--
-- PDU SESSION RESOURCE SETUP RESPONSE
--
-- **************************************************************
PDUSessionResourceSetupResponse ::= SEQUENCE {
protocolIEs ProtocolIE-Container { {PDUSessionResourceSetupResponseIEs} },
...
}
PDUSessionResourceSetupResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSetupListSURes CRITICALITY ignore TYPE PDUSessionResourceSetupListSURes PRESENCE optional }|
{ ID id-PDUSessionResourceFailedToSetupListSURes CRITICALITY ignore TYPE PDUSessionResourceFailedToSetupListSURes PRESENCE optional }|
{ ID id-CriticalityDiagnostics CRITICALITY ignore TYPE CriticalityDiagnostics PRESENCE optional },
...
}
-- **************************************************************
--
-- PDU Session Resource Release Elementary Procedure
--
-- **************************************************************
-- **************************************************************
--
-- PDU SESSION RESOURCE RELEASE COMMAND
--
-- **************************************************************
PDUSessionResourceReleaseCommand ::= SEQUENCE {
protocolIEs ProtocolIE-Container { {PDUSessionResourceReleaseCommandIEs} },
...
}
PDUSessionResourceReleaseCommandIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-NAS-PDU CRITICALITY ignore TYPE NAS-PDU PRESENCE optional }|
{ ID id-PDUSessionResourceToReleaseListRelCmd CRITICALITY reject TYPE PDUSessionResourceToReleaseListRelCmd PRESENCE mandatory },
...
}
-- **************************************************************
--
-- PDU SESSION RESOURCE RELEASE RESPONSE
--
-- **************************************************************
PDUSessionResourceReleaseResponse ::= SEQUENCE {
protocolIEs ProtocolIE-Container { {PDUSessionResourceReleaseResponseIEs} },
...
}
PDUSessionResourceReleaseResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceReleasedListRelRes CRITICALITY ignore TYPE PDUSessionResourceReleasedListRelRes PRESENCE mandatory }|
{ ID id-UserLocationInformation CRITICALITY ignore TYPE UserLocationInformation PRESENCE optional }|
{ ID id-CriticalityDiagnostics CRITICALITY ignore TYPE CriticalityDiagnostics PRESENCE optional },
...
}
-- **************************************************************
--
-- PDU Session Resource Modify Elementary Procedure
--
-- **************************************************************
-- **************************************************************
--
-- PDU SESSION RESOURCE MODIFY REQUEST
--
-- **************************************************************
PDUSessionResourceModifyRequest ::= SEQUENCE {
protocolIEs ProtocolIE-Container { {PDUSessionResourceModifyRequestIEs} },
...
}
PDUSessionResourceModifyRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-PDUSessionResourceModifyListModReq CRITICALITY reject TYPE PDUSessionResourceModifyListModReq PRESENCE mandatory },
...
}
-- **************************************************************
--
-- PDU SESSION RESOURCE MODIFY RESPONSE
--
-- **************************************************************
PDUSessionResourceModifyResponse ::= SEQUENCE {
protocolIEs ProtocolIE-Container { {PDUSessionResourceModifyResponseIEs} },
...
}
PDUSessionResourceModifyResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceModifyListModRes CRITICALITY ignore TYPE PDUSessionResourceModifyListModRes PRESENCE optional }|
{ ID id-PDUSessionResourceFailedToModifyListModRes CRITICALITY ignore TYPE PDUSessionResourceFailedToModifyListModRes PRESENCE optional }|
{ ID id-UserLocationInformation CRITICALITY ignore TYPE UserLocationInformation PRESENCE optional }|
{ ID id-CriticalityDiagnostics CRITICALITY ignore TYPE CriticalityDiagnostics PRESENCE optional },
...
}
-- **************************************************************
--
-- PDU Session Resource Notify Elementary Procedure
--
-- **************************************************************
-- **************************************************************
--
-- PDU SESSION RESOURCE NOTIFY
--
-- **************************************************************
PDUSessionResourceNotify ::= SEQUENCE {
protocolIEs ProtocolIE-Container { {PDUSessionResourceNotifyIEs} },
...
}
PDUSessionResourceNotifyIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceNotifyList CRITICALITY reject TYPE PDUSessionResourceNotifyList PRESENCE optional }|
{ ID id-PDUSessionResourceReleasedListNot CRITICALITY ignore TYPE PDUSessionResourceReleasedListNot PRESENCE optional }|
{ ID id-UserLocationInformation CRITICALITY ignore TYPE UserLocationInformation PRESENCE optional },
...
}
-- **************************************************************
--
-- PDU Session Resource Modify Indication Elementary Procedure
--
-- **************************************************************
-- **************************************************************
--
-- PDU SESSION RESOURCE MODIFY INDICATION
--
-- **************************************************************
PDUSessionResourceModifyIndication ::= SEQUENCE {
protocolIEs ProtocolIE-Container { {PDUSessionResourceModifyIndicationIEs} },
...
}
PDUSessionResourceModifyIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceModifyListModInd CRITICALITY reject TYPE PDUSessionResourceModifyListModInd PRESENCE mandatory },
...
}
-- **************************************************************
--
-- PDU SESSION RESOURCE MODIFY CONFIRM
--
-- **************************************************************
PDUSessionResourceModifyConfirm ::= SEQUENCE {
protocolIEs ProtocolIE-Container { {PDUSessionResourceModifyConfirmIEs} },
...
}
PDUSessionResourceModifyConfirmIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceModifyListModCfm CRITICALITY ignore TYPE PDUSessionResourceModifyListModCfm PRESENCE optional }|
{ ID id-PDUSessionResourceFailedToModifyListModCfm CRITICALITY ignore TYPE PDUSessionResourceFailedToModifyListModCfm PRESENCE optional }|
{ ID id-CriticalityDiagnostics CRITICALITY ignore TYPE CriticalityDiagnostics PRESENCE optional },
...
}
-- **************************************************************
--
-- UE CONTEXT MANAGEMENT ELEMENTARY PROCEDURES
--
-- **************************************************************
-- **************************************************************
--
-- Initial Context Setup Elementary Procedure
--
-- **************************************************************
-- **************************************************************
--
-- INITIAL CONTEXT SETUP REQUEST
--
-- **************************************************************
InitialContextSetupRequest ::= SEQUENCE {
protocolIEs ProtocolIE-Container { {InitialContextSetupRequestIEs} },
...
}
InitialContextSetupRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-OldAMF CRITICALITY reject TYPE AMFName PRESENCE optional }|
{ ID id-UEAggregateMaximumBitRate CRITICALITY reject TYPE UEAggregateMaximumBitRate PRESENCE conditional }|
{ ID id-CoreNetworkAssistanceInformationForInactive CRITICALITY ignore TYPE CoreNetworkAssistanceInformationForInactive PRESENCE optional }|
{ ID id-GUAMI CRITICALITY reject TYPE GUAMI PRESENCE mandatory }|
{ ID id-PDUSessionResourceSetupListCxtReq CRITICALITY reject TYPE PDUSessionResourceSetupListCxtReq PRESENCE optional }|
{ ID id-AllowedNSSAI CRITICALITY reject TYPE AllowedNSSAI PRESENCE mandatory }|
{ ID id-UESecurityCapabilities CRITICALITY reject TYPE UESecurityCapabilities PRESENCE mandatory }|
{ ID id-SecurityKey CRITICALITY reject TYPE SecurityKey PRESENCE mandatory }|
{ ID id-TraceActivation CRITICALITY ignore TYPE TraceActivation PRESENCE optional }|
{ ID id-MobilityRestrictionList CRITICALITY ignore TYPE MobilityRestrictionList PRESENCE optional }|
{ ID id-UERadioCapability CRITICALITY ignore TYPE UERadioCapability PRESENCE optional }|
{ ID id-IndexToRFSP CRITICALITY ignore TYPE IndexToRFSP PRESENCE optional }|
{ ID id-MaskedIMEISV CRITICALITY ignore TYPE MaskedIMEISV PRESENCE optional }|
{ ID id-NAS-PDU CRITICALITY ignore TYPE NAS-PDU PRESENCE optional }|
{ ID id-EmergencyFallbackIndicator CRITICALITY reject TYPE EmergencyFallbackIndicator PRESENCE optional }|
{ ID id-RRCInactiveTransitionReportRequest CRITICALITY ignore TYPE RRCInactiveTransitionReportRequest PRESENCE optional }|
{ ID id-UERadioCapabilityForPaging CRITICALITY ignore TYPE UERadioCapabilityForPaging PRESENCE optional }|
{ ID id-RedirectionVoiceFallback CRITICALITY ignore TYPE RedirectionVoiceFallback PRESENCE optional }|
{ ID id-LocationReportingRequestType CRITICALITY ignore TYPE LocationReportingRequestType PRESENCE optional }|
{ ID id-CNAssistedRANTuning CRITICALITY ignore TYPE CNAssistedRANTuning PRESENCE optional },
...
}
-- **************************************************************
--
-- INITIAL CONTEXT SETUP RESPONSE
--
-- **************************************************************
InitialContextSetupResponse ::= SEQUENCE {
protocolIEs ProtocolIE-Container { {InitialContextSetupResponseIEs} },
...
}
InitialContextSetupResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSetupListCxtRes CRITICALITY ignore TYPE PDUSessionResourceSetupListCxtRes PRESENCE optional }|
{ ID id-PDUSessionResourceFailedToSetupListCxtRes CRITICALITY ignore TYPE PDUSessionResourceFailedToSetupListCxtRes PRESENCE optional }|
{ ID id-CriticalityDiagnostics CRITICALITY ignore TYPE CriticalityDiagnostics PRESENCE optional },
...
}
-- **************************************************************
--
-- INITIAL CONTEXT SETUP FAILURE
--
-- **************************************************************
InitialContextSetupFailure ::= SEQUENCE {
protocolIEs ProtocolIE-Container { {InitialContextSetupFailureIEs} },
...
}
InitialContextSetupFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceFailedToSetupListCxtFail CRITICALITY ignore TYPE PDUSessionResourceFailedToSetupListCxtFail PRESENCE optional }|
{ ID id-Cause CRITICALITY ignore TYPE Cause PRESENCE mandatory }|
{ ID id-CriticalityDiagnostics CRITICALITY ignore TYPE CriticalityDiagnostics PRESENCE optional },
...
}
-- **************************************************************
--
-- UE Context Release Request Elementary Procedure
--
-- **************************************************************
-- **************************************************************
--
-- UE CONTEXT RELEASE REQUEST
--
-- **************************************************************
UEContextReleaseRequest ::= SEQUENCE {
protocolIEs ProtocolIE-Container { {UEContextReleaseRequest-IEs} },
...
}
UEContextReleaseRequest-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceListCxtRelReq CRITICALITY reject TYPE PDUSessionResourceListCxtRelReq PRESENCE optional }|
{ ID id-Cause CRITICALITY ignore TYPE Cause PRESENCE mandatory },
...
}
-- **************************************************************
--
-- UE Context Release Elementary Procedure
--
-- **************************************************************
-- **************************************************************
--
-- UE CONTEXT RELEASE COMMAND
--
-- **************************************************************
UEContextReleaseCommand ::= SEQUENCE {
protocolIEs ProtocolIE-Container { {UEContextReleaseCommand-IEs} },
...
}
UEContextReleaseCommand-IEs NGAP-PROTOCOL-IES ::= {
{ ID id-UE-NGAP-IDs CRITICALITY reject TYPE UE-NGAP-IDs PRESENCE mandatory }|
{ ID id-Cause CRITICALITY ignore TYPE Cause PRESENCE mandatory },
...
}
-- **************************************************************
--
-- UE CONTEXT RELEASE COMPLETE
--
-- **************************************************************
UEContextReleaseComplete ::= SEQUENCE {
protocolIEs ProtocolIE-Container { {UEContextReleaseComplete-IEs} },
...
}
UEContextReleaseComplete-IEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-UserLocationInformation CRITICALITY ignore TYPE UserLocationInformation PRESENCE optional }|
{ ID id-InfoOnRecommendedCellsAndRANNodesForPaging CRITICALITY ignore TYPE InfoOnRecommendedCellsAndRANNodesForPaging PRESENCE optional }|
{ ID id-PDUSessionResourceListCxtRelCpl CRITICALITY reject TYPE PDUSessionResourceListCxtRelCpl PRESENCE optional }|
{ ID id-CriticalityDiagnostics CRITICALITY ignore TYPE CriticalityDiagnostics PRESENCE optional },
...
}
-- **************************************************************
--
-- UE Context Modification Elementary Procedure
--
-- **************************************************************
-- **************************************************************
--
-- UE CONTEXT MODIFICATION REQUEST
--
-- **************************************************************
UEContextModificationRequest ::= SEQUENCE {
protocolIEs ProtocolIE-Container { {UEContextModificationRequestIEs} },
...
}
UEContextModificationRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-SecurityKey CRITICALITY reject TYPE SecurityKey PRESENCE optional }|
{ ID id-IndexToRFSP CRITICALITY ignore TYPE IndexToRFSP PRESENCE optional }|
{ ID id-UEAggregateMaximumBitRate CRITICALITY ignore TYPE UEAggregateMaximumBitRate PRESENCE optional }|
{ ID id-UESecurityCapabilities CRITICALITY reject TYPE UESecurityCapabilities PRESENCE optional }|
{ ID id-CoreNetworkAssistanceInformationForInactive CRITICALITY ignore TYPE CoreNetworkAssistanceInformationForInactive PRESENCE optional }|
{ ID id-EmergencyFallbackIndicator CRITICALITY reject TYPE EmergencyFallbackIndicator PRESENCE optional }|
{ ID id-NewAMF-UE-NGAP-ID CRITICALITY reject TYPE AMF-UE-NGAP-ID PRESENCE optional }|
{ ID id-RRCInactiveTransitionReportRequest CRITICALITY ignore TYPE RRCInactiveTransitionReportRequest PRESENCE optional }|
{ ID id-NewGUAMI CRITICALITY reject TYPE GUAMI PRESENCE optional }|
{ ID id-CNAssistedRANTuning CRITICALITY ignore TYPE CNAssistedRANTuning PRESENCE optional },
...
}
-- **************************************************************
--
-- UE CONTEXT MODIFICATION RESPONSE
--
-- **************************************************************
UEContextModificationResponse ::= SEQUENCE {
protocolIEs ProtocolIE-Container { {UEContextModificationResponseIEs} },
...
}
UEContextModificationResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-RRCState CRITICALITY ignore TYPE RRCState PRESENCE optional }|
{ ID id-UserLocationInformation CRITICALITY ignore TYPE UserLocationInformation PRESENCE optional }|
{ ID id-CriticalityDiagnostics CRITICALITY ignore TYPE CriticalityDiagnostics PRESENCE optional },
...
}
-- **************************************************************
--
-- UE CONTEXT MODIFICATION FAILURE
--
-- **************************************************************
UEContextModificationFailure ::= SEQUENCE {
protocolIEs ProtocolIE-Container { {UEContextModificationFailureIEs} },
...
}
UEContextModificationFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- RRC INACTIVE TRANSITION REPORT
--
-- **************************************************************
RRCInactiveTransitionReport ::= SEQUENCE {
protocolIEs ProtocolIE-Container { {RRCInactiveTransitionReportIEs} },
...
}
RRCInactiveTransitionReportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RRCState CRITICALITY ignore TYPE RRCState PRESENCE mandatory }|
{ ID id-UserLocationInformation CRITICALITY ignore TYPE UserLocationInformation PRESENCE mandatory },
...
}
-- **************************************************************
--
-- UE MOBILITY MANAGEMENT ELEMENTARY PROCEDURES
--
-- **************************************************************
-- **************************************************************
--
-- Handover Preparation Elementary Procedure
--
-- **************************************************************
-- **************************************************************
--
-- HANDOVER REQUIRED
--
-- **************************************************************
HandoverRequired ::= SEQUENCE {
protocolIEs ProtocolIE-Container { {HandoverRequiredIEs} },
...
}
HandoverRequiredIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-HandoverType CRITICALITY reject TYPE HandoverType PRESENCE mandatory }|
{ ID id-Cause CRITICALITY ignore TYPE Cause PRESENCE mandatory }|
{ ID id-TargetID CRITICALITY reject TYPE TargetID PRESENCE mandatory }|
{ ID id-DirectForwardingPathAvailability CRITICALITY ignore TYPE DirectForwardingPathAvailability PRESENCE optional }|
{ ID id-PDUSessionResourceListHORqd CRITICALITY reject TYPE PDUSessionResourceListHORqd PRESENCE mandatory }|
{ ID id-SourceToTarget-TransparentContainer CRITICALITY reject TYPE SourceToTarget-TransparentContainer PRESENCE mandatory },
...
}
-- **************************************************************
--
-- HANDOVER COMMAND
--
-- **************************************************************
HandoverCommand ::= SEQUENCE {
protocolIEs ProtocolIE-Container { {HandoverCommandIEs} },
...
}
HandoverCommandIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-HandoverType CRITICALITY reject TYPE HandoverType PRESENCE mandatory }|
{ ID id-NASSecurityParametersFromNGRAN CRITICALITY reject TYPE NASSecurityParametersFromNGRAN PRESENCE conditional }|
-- This IE shall be present if HandoverType IE is set to value "5GStoEPPS" --
{ ID id-PDUSessionResourceHandoverList CRITICALITY ignore TYPE PDUSessionResourceHandoverList PRESENCE optional }|
{ ID id-PDUSessionResourceToReleaseListHOCmd CRITICALITY ignore TYPE PDUSessionResourceToReleaseListHOCmd PRESENCE optional }|
{ ID id-TargetToSource-TransparentContainer CRITICALITY reject TYPE TargetToSource-TransparentContainer PRESENCE mandatory }|
{ ID id-CriticalityDiagnostics CRITICALITY ignore TYPE CriticalityDiagnostics PRESENCE optional },
...
}
-- **************************************************************
--
-- HANDOVER PREPARATION FAILURE
--
-- **************************************************************
HandoverPreparationFailure ::= SEQUENCE {
protocolIEs ProtocolIE-Container { {HandoverPreparationFailureIEs} },
...
}
HandoverPreparationFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- Handover Resource Allocation Elementary Procedure
--
-- **************************************************************
-- **************************************************************
--
-- HANDOVER REQUEST
--
-- **************************************************************
HandoverRequest ::= SEQUENCE {
protocolIEs ProtocolIE-Container { {HandoverRequestIEs} },
...
}
HandoverRequestIEs NGAP-PROTOCOL-IES ::= {
{ ID id-AMF-UE-NGAP-ID CRITICALITY reject TYPE AMF-UE-NGAP-ID PRESENCE mandatory }|
{ ID id-HandoverType CRITICALITY reject TYPE HandoverType PRESENCE mandatory }|
{ ID id-Cause CRITICALITY ignore TYPE Cause PRESENCE mandatory }|
{ ID id-UEAggregateMaximumBitRate CRITICALITY reject TYPE UEAggregateMaximumBitRate PRESENCE mandatory }|
{ ID id-CoreNetworkAssistanceInformationForInactive CRITICALITY ignore TYPE CoreNetworkAssistanceInformationForInactive PRESENCE optional }|
{ ID id-UESecurityCapabilities CRITICALITY reject TYPE UESecurityCapabilities PRESENCE mandatory }|
{ ID id-SecurityContext CRITICALITY reject TYPE SecurityContext PRESENCE mandatory }|
{ ID id-NewSecurityContextInd CRITICALITY reject TYPE NewSecurityContextInd PRESENCE optional }|
{ ID id-NASC CRITICALITY reject TYPE NAS-PDU PRESENCE optional }|
{ ID id-PDUSessionResourceSetupListHOReq CRITICALITY reject TYPE PDUSessionResourceSetupListHOReq PRESENCE mandatory }|
{ ID id-AllowedNSSAI CRITICALITY reject TYPE AllowedNSSAI PRESENCE mandatory }|
{ ID id-TraceActivation CRITICALITY ignore TYPE TraceActivation PRESENCE optional }|
{ ID id-MaskedIMEISV CRITICALITY ignore TYPE MaskedIMEISV PRESENCE optional }|
{ ID id-SourceToTarget-TransparentContainer CRITICALITY reject TYPE SourceToTarget-TransparentContainer PRESENCE mandatory }|
{ ID id-MobilityRestrictionList CRITICALITY ignore TYPE MobilityRestrictionList PRESENCE optional }|
{ ID id-LocationReportingRequestType CRITICALITY ignore TYPE LocationReportingRequestType PRESENCE optional }|
{ ID id-RRCInactiveTransitionReportRequest CRITICALITY ignore TYPE RRCInactiveTransitionReportRequest PRESENCE optional }|
{ ID id-GUAMI CRITICALITY reject TYPE GUAMI PRESENCE mandatory }|
{ ID id-RedirectionVoiceFallback CRITICALITY ignore TYPE RedirectionVoiceFallback PRESENCE optional }|
{ ID id-CNAssistedRANTuning CRITICALITY ignore TYPE CNAssistedRANTuning PRESENCE optional },
...
}
-- **************************************************************
--
-- HANDOVER REQUEST ACKNOWLEDGE
--
-- **************************************************************
HandoverRequestAcknowledge ::= SEQUENCE {
protocolIEs ProtocolIE-Container { {HandoverRequestAcknowledgeIEs} },
...
}
HandoverRequestAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceAdmittedList CRITICALITY ignore TYPE PDUSessionResourceAdmittedList PRESENCE mandatory }|
{ ID id-PDUSessionResourceFailedToSetupListHOAck CRITICALITY ignore TYPE PDUSessionResourceFailedToSetupListHOAck PRESENCE optional }|
{ ID id-TargetToSource-TransparentContainer CRITICALITY reject TYPE TargetToSource-TransparentContainer PRESENCE mandatory }|
{ ID id-CriticalityDiagnostics CRITICALITY ignore TYPE CriticalityDiagnostics PRESENCE optional },
...
}
-- **************************************************************
--
-- HANDOVER FAILURE
--
-- **************************************************************
HandoverFailure ::= SEQUENCE {
protocolIEs ProtocolIE-Container { { HandoverFailureIEs} },
...
}
HandoverFailureIEs NGAP-PROTOCOL-IES ::= {
{ ID id-AMF-UE-NGAP-ID CRITICALITY ignore TYPE AMF-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- Handover Notification Elementary Procedure
--
-- **************************************************************
-- **************************************************************
--
-- HANDOVER NOTIFY
--
-- **************************************************************
HandoverNotify ::= SEQUENCE {
protocolIEs ProtocolIE-Container { { HandoverNotifyIEs} },
...
}
HandoverNotifyIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UserLocationInformation CRITICALITY ignore TYPE UserLocationInformation PRESENCE mandatory },
...
}
-- **************************************************************
--
-- Path Switch Request Elementary Procedure
--
-- **************************************************************
-- **************************************************************
--
-- PATH SWITCH REQUEST
--
-- **************************************************************
PathSwitchRequest ::= SEQUENCE {
protocolIEs ProtocolIE-Container { { PathSwitchRequestIEs} },
...
}
PathSwitchRequestIEs NGAP-PROTOCOL-IES ::= {
{ ID id-RAN-UE-NGAP-ID CRITICALITY reject TYPE RAN-UE-NGAP-ID PRESENCE mandatory }|
{ ID id-SourceAMF-UE-NGAP-ID CRITICALITY reject TYPE AMF-UE-NGAP-ID PRESENCE mandatory }|
{ ID id-UserLocationInformation CRITICALITY ignore TYPE UserLocationInformation PRESENCE mandatory }|
{ ID id-UESecurityCapabilities CRITICALITY ignore TYPE UESecurityCapabilities PRESENCE mandatory }|
{ ID id-PDUSessionResourceToBeSwitchedDLList CRITICALITY reject TYPE PDUSessionResourceToBeSwitchedDLList PRESENCE mandatory }|
{ ID id-PDUSessionResourceFailedToSetupListPSReq CRITICALITY ignore TYPE PDUSessionResourceFailedToSetupListPSReq PRESENCE optional },
...
}
-- **************************************************************
--
-- PATH SWITCH REQUEST ACKNOWLEDGE
--
-- **************************************************************
PathSwitchRequestAcknowledge ::= SEQUENCE {
protocolIEs ProtocolIE-Container { { PathSwitchRequestAcknowledgeIEs} },
...
}
PathSwitchRequestAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-UESecurityCapabilities CRITICALITY reject TYPE UESecurityCapabilities PRESENCE optional }|
{ ID id-SecurityContext CRITICALITY reject TYPE SecurityContext PRESENCE mandatory }|
{ ID id-NewSecurityContextInd CRITICALITY reject TYPE NewSecurityContextInd PRESENCE optional }|
{ ID id-PDUSessionResourceSwitchedList CRITICALITY ignore TYPE PDUSessionResourceSwitchedList PRESENCE mandatory }|
{ ID id-PDUSessionResourceReleasedListPSAck CRITICALITY ignore TYPE PDUSessionResourceReleasedListPSAck PRESENCE optional }|
{ ID id-AllowedNSSAI CRITICALITY reject TYPE AllowedNSSAI PRESENCE mandatory }|
{ ID id-CoreNetworkAssistanceInformationForInactive CRITICALITY ignore TYPE CoreNetworkAssistanceInformationForInactive PRESENCE optional }|
{ ID id-RRCInactiveTransitionReportRequest CRITICALITY ignore TYPE RRCInactiveTransitionReportRequest PRESENCE optional }|
{ ID id-CriticalityDiagnostics CRITICALITY ignore TYPE CriticalityDiagnostics PRESENCE optional }|
{ ID id-RedirectionVoiceFallback CRITICALITY ignore TYPE RedirectionVoiceFallback PRESENCE optional }|
{ ID id-CNAssistedRANTuning CRITICALITY ignore TYPE CNAssistedRANTuning PRESENCE optional },
...
}
-- **************************************************************
--
-- PATH SWITCH REQUEST FAILURE
--
-- **************************************************************
PathSwitchRequestFailure ::= SEQUENCE {
protocolIEs ProtocolIE-Container { { PathSwitchRequestFailureIEs} },
...
}
PathSwitchRequestFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceReleasedListPSFail CRITICALITY ignore TYPE PDUSessionResourceReleasedListPSFail PRESENCE mandatory }|
{ ID id-CriticalityDiagnostics CRITICALITY ignore TYPE CriticalityDiagnostics PRESENCE optional },
...
}
-- **************************************************************
--
-- Handover Cancellation Elementary Procedure
--
-- **************************************************************
-- **************************************************************
--
-- HANDOVER CANCEL
--
-- **************************************************************
HandoverCancel ::= SEQUENCE {
protocolIEs ProtocolIE-Container { { HandoverCancelIEs} },
...
}
HandoverCancelIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-Cause CRITICALITY ignore TYPE Cause PRESENCE mandatory },
...
}
-- **************************************************************
--
-- HANDOVER CANCEL ACKNOWLEDGE
--
-- **************************************************************
HandoverCancelAcknowledge ::= SEQUENCE {
protocolIEs ProtocolIE-Container { { HandoverCancelAcknowledgeIEs} },
...
}
HandoverCancelAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-CriticalityDiagnostics CRITICALITY ignore TYPE CriticalityDiagnostics PRESENCE optional },
...
}
-- **************************************************************
--
-- Uplink RAN Status Transfer Elementary Procedure
--
-- **************************************************************
-- **************************************************************
--
-- UPLINK RAN STATUS TRANSFER
--
-- **************************************************************
UplinkRANStatusTransfer ::= SEQUENCE {
protocolIEs ProtocolIE-Container { {UplinkRANStatusTransferIEs} },
...
}
UplinkRANStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANStatusTransfer-TransparentContainer CRITICALITY reject TYPE RANStatusTransfer-TransparentContainer PRESENCE mandatory },
...
}
-- **************************************************************
--
-- Downlink RAN Status Transfer Elementary Procedure
--
-- **************************************************************
-- **************************************************************
--
-- DOWNLINK RAN STATUS TRANSFER
--
-- **************************************************************
DownlinkRANStatusTransfer ::= SEQUENCE {
protocolIEs ProtocolIE-Container { {DownlinkRANStatusTransferIEs} },
...
}
DownlinkRANStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANStatusTransfer-TransparentContainer CRITICALITY reject TYPE RANStatusTransfer-TransparentContainer PRESENCE mandatory },
...
}
-- **************************************************************
--
-- PAGING ELEMENTARY PROCEDURE
--
-- **************************************************************
-- **************************************************************
--
-- PAGING
--
-- **************************************************************
Paging ::= SEQUENCE {
protocolIEs ProtocolIE-Container { {PagingIEs} },
...
}
PagingIEs NGAP-PROTOCOL-IES ::= {
{ ID id-UEPagingIdentity CRITICALITY ignore TYPE UEPagingIdentity PRESENCE mandatory }|
{ ID id-PagingDRX CRITICALITY ignore TYPE PagingDRX PRESENCE optional }|
{ ID id-TAIListForPaging CRITICALITY ignore TYPE TAIListForPaging PRESENCE mandatory }|
{ ID id-PagingPriority CRITICALITY ignore TYPE PagingPriority PRESENCE optional }|
{ ID id-UERadioCapabilityForPaging CRITICALITY ignore TYPE UERadioCapabilityForPaging PRESENCE optional }|
{ ID id-PagingOrigin CRITICALITY ignore TYPE PagingOrigin PRESENCE optional }|
{ ID id-AssistanceDataForPaging CRITICALITY ignore TYPE AssistanceDataForPaging PRESENCE optional },
...
}
-- **************************************************************
--
-- NAS TRANSPORT ELEMENTARY PROCEDURES
--
-- **************************************************************
-- **************************************************************
--
-- INITIAL UE MESSAGE
--
-- **************************************************************
InitialUEMessage ::= SEQUENCE {
protocolIEs ProtocolIE-Container { {InitialUEMessage-IEs} },
...
}
InitialUEMessage-IEs NGAP-PROTOCOL-IES ::= {
{ ID id-RAN-UE-NGAP-ID CRITICALITY reject TYPE RAN-UE-NGAP-ID PRESENCE mandatory }|
{ ID id-NAS-PDU CRITICALITY reject TYPE NAS-PDU PRESENCE mandatory }|
{ ID id-UserLocationInformation CRITICALITY reject TYPE UserLocationInformation PRESENCE mandatory }|
{ ID id-RRCEstablishmentCause CRITICALITY ignore TYPE RRCEstablishmentCause PRESENCE mandatory }|
{ ID id-FiveG-S-TMSI CRITICALITY reject TYPE FiveG-S-TMSI PRESENCE optional }|
{ ID id-AMFSetID CRITICALITY ignore TYPE AMFSetID PRESENCE optional }|
{ ID id-UEContextRequest CRITICALITY ignore TYPE UEContextRequest PRESENCE optional }|
{ ID id-AllowedNSSAI CRITICALITY reject TYPE AllowedNSSAI PRESENCE optional }|
{ ID id-SourceToTarget-AMFInformationReroute CRITICALITY ignore TYPE SourceToTarget-AMFInformationReroute PRESENCE optional }|
{ ID id-SelectedPLMNIdentity CRITICALITY ignore TYPE PLMNIdentity PRESENCE optional },
...
}
-- **************************************************************
--
-- DOWNLINK NAS TRANSPORT
--
-- **************************************************************
DownlinkNASTransport ::= SEQUENCE {
protocolIEs ProtocolIE-Container { {DownlinkNASTransport-IEs} },
...
}
DownlinkNASTransport-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-OldAMF CRITICALITY reject TYPE AMFName PRESENCE optional }|
{ ID id-RANPagingPriority CRITICALITY ignore TYPE RANPagingPriority PRESENCE optional }|
{ ID id-NAS-PDU CRITICALITY reject TYPE NAS-PDU PRESENCE mandatory }|
{ ID id-MobilityRestrictionList CRITICALITY ignore TYPE MobilityRestrictionList PRESENCE optional }|
{ ID id-IndexToRFSP CRITICALITY ignore TYPE IndexToRFSP PRESENCE optional }|
{ ID id-UEAggregateMaximumBitRate CRITICALITY ignore TYPE UEAggregateMaximumBitRate PRESENCE optional }|
{ ID id-AllowedNSSAI CRITICALITY reject TYPE AllowedNSSAI PRESENCE optional },
...
}
-- **************************************************************
--
-- UPLINK NAS TRANSPORT
--
-- **************************************************************
UplinkNASTransport ::= SEQUENCE {
protocolIEs ProtocolIE-Container { {UplinkNASTransport-IEs} },
...
}
UplinkNASTransport-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NAS-PDU CRITICALITY reject TYPE NAS-PDU PRESENCE mandatory }|
{ ID id-UserLocationInformation CRITICALITY ignore TYPE UserLocationInformation PRESENCE mandatory },
...
}
-- **************************************************************
--
-- NAS NON DELIVERY INDICATION
--
-- **************************************************************
NASNonDeliveryIndication ::= SEQUENCE {
protocolIEs ProtocolIE-Container { {NASNonDeliveryIndication-IEs} },
...
}
NASNonDeliveryIndication-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NAS-PDU CRITICALITY ignore TYPE NAS-PDU PRESENCE mandatory }|
{ ID id-Cause CRITICALITY ignore TYPE Cause PRESENCE mandatory },
...
}
-- **************************************************************
--
-- REROUTE NAS REQUEST
--
-- **************************************************************
RerouteNASRequest ::= SEQUENCE {
protocolIEs ProtocolIE-Container { {RerouteNASRequest-IEs} },
...
}
RerouteNASRequest-IEs NGAP-PROTOCOL-IES ::= {
{ ID id-RAN-UE-NGAP-ID CRITICALITY reject TYPE RAN-UE-NGAP-ID PRESENCE mandatory }|
{ ID id-AMF-UE-NGAP-ID CRITICALITY ignore TYPE AMF-UE-NGAP-ID PRESENCE optional }|
{ ID id-NGAP-Message CRITICALITY reject TYPE OCTET STRING PRESENCE mandatory }|
{ ID id-AMFSetID CRITICALITY reject TYPE AMFSetID PRESENCE mandatory }|
{ ID id-AllowedNSSAI CRITICALITY reject TYPE AllowedNSSAI PRESENCE optional }|
{ ID id-SourceToTarget-AMFInformationReroute CRITICALITY ignore TYPE SourceToTarget-AMFInformationReroute PRESENCE optional },
...
}
-- **************************************************************
--
-- INTERFACE MANAGEMENT ELEMENTARY PROCEDURES
--
-- **************************************************************
-- **************************************************************
--
-- NG Setup Elementary Procedure
--
-- **************************************************************
-- **************************************************************
--
-- NG SETUP REQUEST
--
-- **************************************************************
NGSetupRequest ::= SEQUENCE {
protocolIEs ProtocolIE-Container { {NGSetupRequestIEs} },
...
}
NGSetupRequestIEs NGAP-PROTOCOL-IES ::= {
{ ID id-GlobalRANNodeID CRITICALITY reject TYPE GlobalRANNodeID PRESENCE mandatory }|
{ ID id-RANNodeName CRITICALITY ignore TYPE RANNodeName PRESENCE optional}|
{ ID id-SupportedTAList CRITICALITY reject TYPE SupportedTAList PRESENCE mandatory }|
{ ID id-DefaultPagingDRX CRITICALITY ignore TYPE PagingDRX PRESENCE mandatory }|
{ ID id-UERetentionInformation CRITICALITY ignore TYPE UERetentionInformation PRESENCE optional },
...
}
-- **************************************************************
--
-- NG SETUP RESPONSE
--
-- **************************************************************
NGSetupResponse ::= SEQUENCE {
protocolIEs ProtocolIE-Container { {NGSetupResponseIEs} },
...
}
NGSetupResponseIEs NGAP-PROTOCOL-IES ::= {
{ ID id-AMFName CRITICALITY reject TYPE AMFName PRESENCE mandatory }|
{ ID id-ServedGUAMIList CRITICALITY reject TYPE ServedGUAMIList PRESENCE mandatory }|
{ ID id-RelativeAMFCapacity CRITICALITY ignore TYPE RelativeAMFCapacity PRESENCE mandatory }|
{ ID id-PLMNSupportList CRITICALITY reject TYPE PLMNSupportList PRESENCE mandatory }|
{ ID id-CriticalityDiagnostics CRITICALITY ignore TYPE CriticalityDiagnostics PRESENCE optional }|
{ ID id-UERetentionInformation CRITICALITY ignore TYPE UERetentionInformation PRESENCE optional },
...
}
-- **************************************************************
--
-- NG SETUP FAILURE
--
-- **************************************************************
NGSetupFailure ::= SEQUENCE {
protocolIEs ProtocolIE-Container { {NGSetupFailureIEs} },
...
}
NGSetupFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- RAN Configuration Update Elementary Procedure
--
-- **************************************************************
-- **************************************************************
--
-- RAN CONFIGURATION UPDATE
--
-- **************************************************************
RANConfigurationUpdate ::= SEQUENCE {
protocolIEs ProtocolIE-Container { {RANConfigurationUpdateIEs} },
...
}
RANConfigurationUpdateIEs NGAP-PROTOCOL-IES ::= {
{ ID id-RANNodeName CRITICALITY ignore TYPE RANNodeName PRESENCE optional }|
{ ID id-SupportedTAList CRITICALITY reject TYPE SupportedTAList PRESENCE optional }|
{ ID id-DefaultPagingDRX CRITICALITY ignore TYPE PagingDRX PRESENCE optional }|
{ ID id-GlobalRANNodeID CRITICALITY ignore TYPE GlobalRANNodeID PRESENCE optional }|
{ ID id-NGRAN-TNLAssociationToRemoveList CRITICALITY reject TYPE NGRAN-TNLAssociationToRemoveList PRESENCE optional },
...
}
-- **************************************************************
--
-- RAN CONFIGURATION UPDATE ACKNOWLEDGE
--
-- **************************************************************
RANConfigurationUpdateAcknowledge ::= SEQUENCE {
protocolIEs ProtocolIE-Container { {RANConfigurationUpdateAcknowledgeIEs} },
...
}
RANConfigurationUpdateAcknowledgeIEs NGAP-PROTOCOL-IES ::= {
{ ID id-CriticalityDiagnostics CRITICALITY ignore TYPE CriticalityDiagnostics PRESENCE optional },
...
}
-- **************************************************************
--
-- RAN CONFIGURATION UPDATE FAILURE
--
-- **************************************************************
RANConfigurationUpdateFailure ::= SEQUENCE {
protocolIEs ProtocolIE-Container { {RANConfigurationUpdateFailureIEs} },
...
}
RANConfigurationUpdateFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- AMF Configuration Update Elementary Procedure
--
-- **************************************************************
-- **************************************************************
--
-- AMF CONFIGURATION UPDATE
--
-- **************************************************************
AMFConfigurationUpdate ::= SEQUENCE {
protocolIEs ProtocolIE-Container { {AMFConfigurationUpdateIEs} },
...
}
AMFConfigurationUpdateIEs NGAP-PROTOCOL-IES ::= {
{ ID id-AMFName CRITICALITY reject TYPE AMFName PRESENCE optional }|
{ ID id-ServedGUAMIList CRITICALITY reject TYPE ServedGUAMIList PRESENCE optional }|
{ ID id-RelativeAMFCapacity CRITICALITY ignore TYPE RelativeAMFCapacity PRESENCE optional }|
{ ID id-PLMNSupportList CRITICALITY reject TYPE PLMNSupportList PRESENCE optional }|
{ ID id-AMF-TNLAssociationToAddList CRITICALITY ignore TYPE AMF-TNLAssociationToAddList PRESENCE optional }|
{ ID id-AMF-TNLAssociationToRemoveList CRITICALITY ignore TYPE AMF-TNLAssociationToRemoveList PRESENCE optional }|
{ ID id-AMF-TNLAssociationToUpdateList CRITICALITY ignore TYPE AMF-TNLAssociationToUpdateList PRESENCE optional },
...
}
-- **************************************************************
--
-- AMF CONFIGURATION UPDATE ACKNOWLEDGE
--
-- **************************************************************
AMFConfigurationUpdateAcknowledge ::= SEQUENCE {
protocolIEs ProtocolIE-Container { {AMFConfigurationUpdateAcknowledgeIEs} },
...
}
AMFConfigurationUpdateAcknowledgeIEs NGAP-PROTOCOL-IES ::= {
{ ID id-AMF-TNLAssociationSetupList CRITICALITY ignore TYPE AMF-TNLAssociationSetupList PRESENCE optional }|
{ ID id-AMF-TNLAssociationFailedToSetupList CRITICALITY ignore TYPE TNLAssociationList PRESENCE optional }|
{ ID id-CriticalityDiagnostics CRITICALITY ignore TYPE CriticalityDiagnostics PRESENCE optional },
...
}
-- **************************************************************
--
-- AMF CONFIGURATION UPDATE FAILURE
--
-- **************************************************************
AMFConfigurationUpdateFailure ::= SEQUENCE {
protocolIEs ProtocolIE-Container { {AMFConfigurationUpdateFailureIEs} },
...
}
AMFConfigurationUpdateFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- AMF Status Indication Elementary Procedure
--
-- **************************************************************
-- **************************************************************
--
-- AMF STATUS INDICATION
--
-- **************************************************************
AMFStatusIndication ::= SEQUENCE {
protocolIEs ProtocolIE-Container { {AMFStatusIndicationIEs} },
...
}
AMFStatusIndicationIEs NGAP-PROTOCOL-IES ::= {
{ ID id-UnavailableGUAMIList CRITICALITY reject TYPE UnavailableGUAMIList PRESENCE mandatory },
...
}
-- **************************************************************
--
-- NG Reset Elementary Procedure
--
-- **************************************************************
-- **************************************************************
--
-- NG RESET
--
-- **************************************************************
NGReset ::= SEQUENCE {
protocolIEs ProtocolIE-Container { {NGResetIEs} },
...
}
NGResetIEs NGAP-PROTOCOL-IES ::= {
{ ID id-Cause CRITICALITY ignore TYPE Cause PRESENCE mandatory }|
{ ID id-ResetType CRITICALITY reject TYPE ResetType PRESENCE mandatory },
...
}
-- **************************************************************
--
-- NG RESET ACKNOWLEDGE
--
-- **************************************************************
NGResetAcknowledge ::= SEQUENCE {
protocolIEs ProtocolIE-Container { {NGResetAcknowledgeIEs} },
...
}
NGResetAcknowledgeIEs NGAP-PROTOCOL-IES ::= {
{ ID id-UE-associatedLogicalNG-connectionList CRITICALITY ignore TYPE UE-associatedLogicalNG-connectionList PRESENCE optional }|
{ ID id-CriticalityDiagnostics CRITICALITY ignore TYPE CriticalityDiagnostics PRESENCE optional },
...
}
-- **************************************************************
--
-- Error Indication Elementary Procedure
--
-- **************************************************************
-- **************************************************************
--
-- ERROR INDICATION
--
-- **************************************************************
ErrorIndication ::= SEQUENCE {
protocolIEs ProtocolIE-Container { {ErrorIndicationIEs} },
...
}
ErrorIndicationIEs NGAP-PROTOCOL-IES ::= {
{ ID id-AMF-UE-NGAP-ID CRITICALITY ignore TYPE AMF-UE-NGAP-ID PRESENCE optional }|
{ ID id-RAN-UE-NGAP-ID CRITICALITY ignore TYPE RAN-UE-NGAP-ID PRESENCE optional }|
{ ID id-Cause CRITICALITY ignore TYPE Cause PRESENCE optional }|
{ ID id-CriticalityDiagnostics CRITICALITY ignore TYPE CriticalityDiagnostics PRESENCE optional },
...
}
-- **************************************************************
--
-- OVERLOAD START
--
-- **************************************************************
OverloadStart ::= SEQUENCE {
protocolIEs ProtocolIE-Container { {OverloadStartIEs} },
...
}
OverloadStartIEs NGAP-PROTOCOL-IES ::= {
{ ID id-AMFOverloadResponse CRITICALITY reject TYPE OverloadResponse PRESENCE optional }|
{ ID id-AMFTrafficLoadReductionIndication CRITICALITY ignore TYPE TrafficLoadReductionIndication PRESENCE optional }|
{ ID id-OverloadStartNSSAIList CRITICALITY ignore TYPE OverloadStartNSSAIList PRESENCE optional },
...
}
-- **************************************************************
--
-- OVERLOAD STOP
--
-- **************************************************************
OverloadStop ::= SEQUENCE {
protocolIEs ProtocolIE-Container { {OverloadStopIEs} },
...
}
OverloadStopIEs NGAP-PROTOCOL-IES ::= {
...
}
-- **************************************************************
--
-- CONFIGURATION TRANSFER ELEMENTARY PROCEDURES
--
-- **************************************************************
-- **************************************************************
--
-- UPLINK RAN CONFIGURATION TRANSFER
--
-- **************************************************************
UplinkRANConfigurationTransfer ::= SEQUENCE {
protocolIEs ProtocolIE-Container { {UplinkRANConfigurationTransferIEs} },
...
}
UplinkRANConfigurationTransferIEs NGAP-PROTOCOL-IES ::= {
{ ID id-SONConfigurationTransferUL CRITICALITY ignore TYPE SONConfigurationTransfer PRESENCE optional }|
{ ID id-ENDC-SONConfigurationTransferUL CRITICALITY ignore TYPE EN-DCSONConfigurationTransfer PRESENCE optional },
...
}
-- **************************************************************
--
-- DOWNLINK RAN CONFIGURATION TRANSFER
--
-- **************************************************************
DownlinkRANConfigurationTransfer ::= SEQUENCE {
protocolIEs ProtocolIE-Container { {DownlinkRANConfigurationTransferIEs} },
...
}
DownlinkRANConfigurationTransferIEs NGAP-PROTOCOL-IES ::= {
{ ID id-SONConfigurationTransferDL CRITICALITY ignore TYPE SONConfigurationTransfer PRESENCE optional }|
{ ID id-ENDC-SONConfigurationTransferDL CRITICALITY ignore TYPE EN-DCSONConfigurationTransfer PRESENCE optional },
...
}
-- **************************************************************
--
-- WARNING MESSAGE TRANSMISSION ELEMENTARY PROCEDURES
--
-- **************************************************************
-- **************************************************************
--
-- Write-Replace Warning Elementary Procedure
--
-- **************************************************************
-- **************************************************************
--
-- WRITE-REPLACE WARNING REQUEST
--
-- **************************************************************
WriteReplaceWarningRequest ::= SEQUENCE {
protocolIEs ProtocolIE-Container { {WriteReplaceWarningRequestIEs} },
...
}
WriteReplaceWarningRequestIEs NGAP-PROTOCOL-IES ::= {
{ ID id-MessageIdentifier CRITICALITY reject TYPE MessageIdentifier PRESENCE mandatory }|
{ ID id-SerialNumber CRITICALITY reject TYPE SerialNumber PRESENCE mandatory }|
{ ID id-WarningAreaList CRITICALITY ignore TYPE WarningAreaList PRESENCE optional }|
{ ID id-RepetitionPeriod CRITICALITY reject TYPE RepetitionPeriod PRESENCE mandatory }|
{ ID id-NumberOfBroadcastsRequested CRITICALITY reject TYPE NumberOfBroadcastsRequested PRESENCE mandatory }|
{ ID id-WarningType CRITICALITY ignore TYPE WarningType PRESENCE optional }|
{ ID id-WarningSecurityInfo CRITICALITY ignore TYPE WarningSecurityInfo PRESENCE optional }|
{ ID id-DataCodingScheme CRITICALITY ignore TYPE DataCodingScheme PRESENCE optional }|
{ ID id-WarningMessageContents CRITICALITY ignore TYPE WarningMessageContents PRESENCE optional }|
{ ID id-ConcurrentWarningMessageInd CRITICALITY reject TYPE ConcurrentWarningMessageInd PRESENCE optional }|
{ ID id-WarningAreaCoordinates CRITICALITY ignore TYPE WarningAreaCoordinates PRESENCE optional },
...
}
-- **************************************************************
--
-- WRITE-REPLACE WARNING RESPONSE
--
-- **************************************************************
WriteReplaceWarningResponse ::= SEQUENCE {
protocolIEs ProtocolIE-Container { {WriteReplaceWarningResponseIEs} },
...
}
WriteReplaceWarningResponseIEs NGAP-PROTOCOL-IES ::= {
{ ID id-MessageIdentifier CRITICALITY reject TYPE MessageIdentifier PRESENCE mandatory }|
{ ID id-SerialNumber CRITICALITY reject TYPE SerialNumber PRESENCE mandatory }|
{ ID id-BroadcastCompletedAreaList CRITICALITY ignore TYPE BroadcastCompletedAreaList PRESENCE optional }|
{ ID id-CriticalityDiagnostics CRITICALITY ignore TYPE CriticalityDiagnostics PRESENCE optional },
...
}
-- **************************************************************
--
-- PWS Cancel Elementary Procedure
--
-- **************************************************************
-- **************************************************************
--
-- PWS CANCEL REQUEST
--
-- **************************************************************
PWSCancelRequest ::= SEQUENCE {
protocolIEs ProtocolIE-Container { {PWSCancelRequestIEs} },
...
}
PWSCancelRequestIEs NGAP-PROTOCOL-IES ::= {
{ ID id-MessageIdentifier CRITICALITY reject TYPE MessageIdentifier PRESENCE mandatory }|
{ ID id-SerialNumber CRITICALITY reject TYPE SerialNumber PRESENCE mandatory }|
{ ID id-WarningAreaList CRITICALITY ignore TYPE WarningAreaList PRESENCE optional }|
{ ID id-CancelAllWarningMessages CRITICALITY reject TYPE CancelAllWarningMessages PRESENCE optional },
...
}
-- **************************************************************
--
-- PWS CANCEL RESPONSE
--
-- **************************************************************
PWSCancelResponse ::= SEQUENCE {
protocolIEs ProtocolIE-Container { {PWSCancelResponseIEs} },
...
}
PWSCancelResponseIEs NGAP-PROTOCOL-IES ::= {
{ ID id-MessageIdentifier CRITICALITY reject TYPE MessageIdentifier PRESENCE mandatory }|
{ ID id-SerialNumber CRITICALITY reject TYPE SerialNumber PRESENCE mandatory }|
{ ID id-BroadcastCancelledAreaList CRITICALITY ignore TYPE BroadcastCancelledAreaList PRESENCE optional }|
{ ID id-CriticalityDiagnostics CRITICALITY ignore TYPE CriticalityDiagnostics PRESENCE optional },
...
}
-- **************************************************************
--
-- PWS Restart Indication Elementary Procedure
--
-- **************************************************************
-- **************************************************************
--
-- PWS RESTART INDICATION
--
-- **************************************************************
PWSRestartIndication ::= SEQUENCE {
protocolIEs ProtocolIE-Container { {PWSRestartIndicationIEs} },
...
}
PWSRestartIndicationIEs NGAP-PROTOCOL-IES ::= {
{ ID id-CellIDListForRestart CRITICALITY reject TYPE CellIDListForRestart PRESENCE mandatory }|
{ ID id-GlobalRANNodeID CRITICALITY reject TYPE GlobalRANNodeID PRESENCE mandatory }|
{ ID id-TAIListForRestart CRITICALITY reject TYPE TAIListForRestart PRESENCE mandatory }|
{ ID id-EmergencyAreaIDListForRestart CRITICALITY reject TYPE EmergencyAreaIDListForRestart PRESENCE optional },
...
}
-- **************************************************************
--
-- PWS Failure Indication Elementary Procedure
--
-- **************************************************************
-- **************************************************************
--
-- PWS FAILURE INDICATION
--
-- **************************************************************
PWSFailureIndication ::= SEQUENCE {
protocolIEs ProtocolIE-Container { {PWSFailureIndicationIEs} },
...
}
PWSFailureIndicationIEs NGAP-PROTOCOL-IES ::= {
{ ID id-PWSFailedCellIDList CRITICALITY reject TYPE PWSFailedCellIDList PRESENCE mandatory }|
{ ID id-GlobalRANNodeID CRITICALITY reject TYPE GlobalRANNodeID PRESENCE mandatory },
...
}
-- **************************************************************
--
-- NRPPA TRANSPORT ELEMENTARY PROCEDURES
--
-- **************************************************************
-- **************************************************************
--
-- DOWNLINK UE ASSOCIATED NRPPA TRANSPORT
--
-- **************************************************************
DownlinkUEAssociatedNRPPaTransport ::= SEQUENCE {
protocolIEs ProtocolIE-Container { {DownlinkUEAssociatedNRPPaTransportIEs} },
...
}
DownlinkUEAssociatedNRPPaTransportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RoutingID CRITICALITY reject TYPE RoutingID PRESENCE mandatory }|
{ ID id-NRPPa-PDU CRITICALITY reject TYPE NRPPa-PDU PRESENCE mandatory },
...
}
-- **************************************************************
--
-- UPLINK UE ASSOCIATED NRPPA TRANSPORT
--
-- **************************************************************
UplinkUEAssociatedNRPPaTransport ::= SEQUENCE {
protocolIEs ProtocolIE-Container { {UplinkUEAssociatedNRPPaTransportIEs} },
...
}
UplinkUEAssociatedNRPPaTransportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RoutingID CRITICALITY reject TYPE RoutingID PRESENCE mandatory }|
{ ID id-NRPPa-PDU CRITICALITY reject TYPE NRPPa-PDU PRESENCE mandatory },
...
}
-- **************************************************************
--
-- DOWNLINK NON UE ASSOCIATED NRPPA TRANSPORT
--
-- **************************************************************
DownlinkNonUEAssociatedNRPPaTransport ::= SEQUENCE {
protocolIEs ProtocolIE-Container { {DownlinkNonUEAssociatedNRPPaTransportIEs} },
...
}
DownlinkNonUEAssociatedNRPPaTransportIEs NGAP-PROTOCOL-IES ::= {
{ ID id-RoutingID CRITICALITY reject TYPE RoutingID PRESENCE mandatory }|
{ ID id-NRPPa-PDU CRITICALITY reject TYPE NRPPa-PDU PRESENCE mandatory },
...
}
-- **************************************************************
--
-- UPLINK NON UE ASSOCIATED NRPPA TRANSPORT
--
-- **************************************************************
UplinkNonUEAssociatedNRPPaTransport ::= SEQUENCE {
protocolIEs ProtocolIE-Container { {UplinkNonUEAssociatedNRPPaTransportIEs} },
...
}
UplinkNonUEAssociatedNRPPaTransportIEs NGAP-PROTOCOL-IES ::= {
{ ID id-RoutingID CRITICALITY reject TYPE RoutingID PRESENCE mandatory }|
{ ID id-NRPPa-PDU CRITICALITY reject TYPE NRPPa-PDU PRESENCE mandatory },
...
}
-- **************************************************************
--
-- TRACE ELEMENTARY PROCEDURES
--
-- **************************************************************
-- **************************************************************
--
-- TRACE START
--
-- **************************************************************
TraceStart ::= SEQUENCE {
protocolIEs ProtocolIE-Container { {TraceStartIEs} },
...
}
TraceStartIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-TraceActivation CRITICALITY ignore TYPE TraceActivation PRESENCE mandatory },
...
}
-- **************************************************************
--
-- TRACE FAILURE INDICATION
--
-- **************************************************************
TraceFailureIndication ::= SEQUENCE {
protocolIEs ProtocolIE-Container { {TraceFailureIndicationIEs} },
...
}
TraceFailureIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NGRANTraceID CRITICALITY ignore TYPE NGRANTraceID PRESENCE mandatory }|
{ ID id-Cause CRITICALITY ignore TYPE Cause PRESENCE mandatory },
...
}
-- **************************************************************
--
-- DEACTIVATE TRACE
--
-- **************************************************************
DeactivateTrace ::= SEQUENCE {
protocolIEs ProtocolIE-Container { {DeactivateTraceIEs} },
...
}
DeactivateTraceIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NGRANTraceID CRITICALITY ignore TYPE NGRANTraceID PRESENCE mandatory },
...
}
-- **************************************************************
--
-- CELL TRAFFIC TRACE
--
-- **************************************************************
CellTrafficTrace ::= SEQUENCE {
protocolIEs ProtocolIE-Container { {CellTrafficTraceIEs} },
...
}
CellTrafficTraceIEs NGAP-PROTOCOL-IES ::= {
{ID id-AMF-UE-NGAP-ID CRITICALITY reject TYPE AMF-UE-NGAP-ID PRESENCE mandatory }|
{ID id-RAN-UE-NGAP-ID CRITICALITY reject TYPE RAN-UE-NGAP-ID PRESENCE mandatory }|
{ID id-NGRANTraceID CRITICALITY ignore TYPE NGRANTraceID PRESENCE mandatory }|
{ID id-NGRAN-CGI CRITICALITY ignore TYPE NGRAN-CGI PRESENCE mandatory }|
{ID id-TraceCollectionEntityIPAddress CRITICALITY ignore TYPE TransportLayerAddress PRESENCE mandatory },
...
}
-- **************************************************************
--
-- LOCATION REPORTING ELEMENTARY PROCEDURES
--
-- **************************************************************
-- **************************************************************
--
-- LOCATION REPORTING CONTROL
--
-- **************************************************************
LocationReportingControl ::= SEQUENCE {
protocolIEs ProtocolIE-Container { {LocationReportingControlIEs} },
...
}
LocationReportingControlIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-LocationReportingRequestType CRITICALITY ignore TYPE LocationReportingRequestType PRESENCE mandatory },
...
}
-- **************************************************************
--
-- LOCATION REPORTING FAILURE INDICATION
--
-- **************************************************************
LocationReportingFailureIndication ::= SEQUENCE {
protocolIEs ProtocolIE-Container { {LocationReportingFailureIndicationIEs} },
...
}
LocationReportingFailureIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-Cause CRITICALITY ignore TYPE Cause PRESENCE mandatory },
...
}
-- **************************************************************
--
-- LOCATION REPORT
--
-- **************************************************************
LocationReport ::= SEQUENCE {
protocolIEs ProtocolIE-Container { {LocationReportIEs} },
...
}
LocationReportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UserLocationInformation CRITICALITY ignore TYPE UserLocationInformation PRESENCE mandatory }|
{ ID id-UEPresenceInAreaOfInterestList CRITICALITY ignore TYPE UEPresenceInAreaOfInterestList PRESENCE optional }|
{ ID id-LocationReportingRequestType CRITICALITY ignore TYPE LocationReportingRequestType PRESENCE mandatory },
...
}
-- **************************************************************
--
-- UE TNLA BINDING ELEMENTARY PROCEDURES
--
-- **************************************************************
-- **************************************************************
--
-- UE TNLA BINDING RELEASE REQUEST
--
-- **************************************************************
UETNLABindingReleaseRequest ::= SEQUENCE {
protocolIEs ProtocolIE-Container { {UETNLABindingReleaseRequestIEs} },
...
}
UETNLABindingReleaseRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory },
...
}
-- **************************************************************
--
-- UE RADIO CAPABILITY MANAGEMENT ELEMENTARY PROCEDURES
--
-- **************************************************************
-- **************************************************************
--
-- UE RADIO CAPABILITY INFO INDICATION
--
-- **************************************************************
UERadioCapabilityInfoIndication ::= SEQUENCE {
protocolIEs ProtocolIE-Container { {UERadioCapabilityInfoIndicationIEs} },
...
}
UERadioCapabilityInfoIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UERadioCapability CRITICALITY ignore TYPE UERadioCapability PRESENCE mandatory }|
{ ID id-UERadioCapabilityForPaging CRITICALITY ignore TYPE UERadioCapabilityForPaging PRESENCE optional },
...
}
-- **************************************************************
--
-- UE Radio Capability Check Elementary Procedure
--
-- **************************************************************
-- **************************************************************
--
-- UE RADIO CAPABILITY CHECK REQUEST
--
-- **************************************************************
UERadioCapabilityCheckRequest ::= SEQUENCE {
protocolIEs ProtocolIE-Container { {UERadioCapabilityCheckRequestIEs} },
...
}
UERadioCapabilityCheckRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UERadioCapability CRITICALITY ignore TYPE UERadioCapability PRESENCE optional },
...
}
-- **************************************************************
--
-- UE RADIO CAPABILITY CHECK RESPONSE
--
-- **************************************************************
UERadioCapabilityCheckResponse ::= SEQUENCE {
protocolIEs ProtocolIE-Container { {UERadioCapabilityCheckResponseIEs} },
...
}
UERadioCapabilityCheckResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-IMSVoiceSupportIndicator CRITICALITY reject TYPE IMSVoiceSupportIndicator PRESENCE mandatory }|
{ ID id-CriticalityDiagnostics CRITICALITY ignore TYPE CriticalityDiagnostics PRESENCE optional },
...
}
-- **************************************************************
--
-- PRIVATE MESSAGE ELEMENTARY PROCEDURE
--
-- **************************************************************
-- **************************************************************
--
-- PRIVATE MESSAGE
--
-- **************************************************************
PrivateMessage ::= SEQUENCE {
privateIEs PrivateIE-Container { { PrivateMessageIEs } },
...
}
PrivateMessageIEs NGAP-PRIVATE-IES ::= {
...
}
-- **************************************************************
--
-- DATA USAGE REPORTING ELEMENTARY PROCEDURES
--
-- **************************************************************
-- **************************************************************
--
-- SECONDARY RAT DATA USAGE REPORT
--
-- **************************************************************
SecondaryRATDataUsageReport ::= SEQUENCE {
protocolIEs ProtocolIE-Container { {SecondaryRATDataUsageReportIEs} },
...
}
SecondaryRATDataUsageReportIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSecondaryRATUsageList CRITICALITY ignore TYPE PDUSessionResourceSecondaryRATUsageList PRESENCE mandatory }|
{ ID id-HandoverFlag CRITICALITY ignore TYPE HandoverFlag PRESENCE optional }|
{ ID id-UserLocationInformation CRITICALITY ignore TYPE UserLocationInformation PRESENCE optional },
...
}
END

-- **************************************************************
--
-- Information Element Definitions
--
-- **************************************************************
NGAP-IEs {
itu-t (0) identified-organization (4) etsi (0) mobileDomain (0)
ngran-Access (22) modules (3) ngap (1) version1 (1) ngap-IEs (2) }
DEFINITIONS AUTOMATIC TAGS ::=
BEGIN
IMPORTS
id-AdditionalDLForwardingUPTNLInformation,
id-AdditionalULForwardingUPTNLInformation,
id-AdditionalDLQosFlowPerTNLInformation,
id-AdditionalDLUPTNLInformationForHOList,
id-AdditionalNGU-UP-TNLInformation,
id-AdditionalUL-NGU-UP-TNLInformation,
id-Cause,
id-CNTypeRestrictionsForEquivalent,
id-CNTypeRestrictionsForServing,
id-CommonNetworkInstance,
id-DataForwardingNotPossible,
id-DL-NGU-UP-TNLInformation,
id-EndpointIPAddressAndPort,
id-LastEUTRAN-PLMNIdentity,
id-LocationReportingAdditionalInfo,
id-MaximumIntegrityProtectedDataRate-DL,
id-NetworkInstance,
id-OldAssociatedQosFlowList-ULendmarkerexpected,
id-PDUSessionAggregateMaximumBitRate,
id-PDUSessionResourceFailedToSetupListCxtFail,
id-PDUSessionResourceReleaseResponseTransfer,
id-PDUSessionType,
id-PSCellInformation,
id-QosFlowAddOrModifyRequestList,
id-QosFlowSetupRequestList,
id-QosFlowToReleaseList,
id-SCTP-TLAs,
id-SecondaryRATUsageInformation,
id-SecurityIndication,
id-SecurityResult,
id-S-NSSAI,
id-TNLAssociationTransportLayerAddressNGRAN,
id-UL-NGU-UP-TNLInformation,
id-UL-NGU-UP-TNLModifyList,
id-ULForwarding,
id-ULForwardingUP-TNLInformation,
maxnoofAllowedAreas,
maxnoofAllowedS-NSSAIs,
maxnoofBPLMNs,
maxnoofCellIDforWarning,
maxnoofCellinAoI,
maxnoofCellinEAI,
maxnoofCellsingNB,
maxnoofCellsinngeNB,
maxnoofCellinTAI,
maxnoofCellsinUEHistoryInfo,
maxnoofCellsUEMovingTrajectory,
maxnoofDRBs,
maxnoofEmergencyAreaID,
maxnoofEAIforRestart,
maxnoofEPLMNs,
maxnoofEPLMNsPlusOne,
maxnoofE-RABs,
maxnoofErrors,
maxnoofForbTACs,
maxnoofMultiConnectivity,
maxnoofMultiConnectivityMinusOne,
maxnoofNGConnectionsToReset,
maxnoofPDUSessions,
maxnoofPLMNs,
maxnoofQosFlows,
maxnoofRANNodeinAoI,
maxnoofRecommendedCells,
maxnoofRecommendedRANNodes,
maxnoofAoI,
maxnoofServedGUAMIs,
maxnoofSliceItems,
maxnoofTACs,
maxnoofTAIforInactive,
maxnoofTAIforPaging,
maxnoofTAIforRestart,
maxnoofTAIforWarning,
maxnoofTAIinAoI,
maxnoofTimePeriods,
maxnoofTNLAssociations,
maxnoofXnExtTLAs,
maxnoofXnGTP-TLAs,
maxnoofXnTLAs
FROM NGAP-Constants
Criticality,
ProcedureCode,
ProtocolIE-ID,
TriggeringMessage
FROM NGAP-CommonDataTypes
ProtocolExtensionContainer{},
ProtocolIE-Container{},
NGAP-PROTOCOL-EXTENSION,
ProtocolIE-SingleContainer{},
NGAP-PROTOCOL-IES
FROM NGAP-Containers;
-- A
AdditionalDLUPTNLInformationForHOList ::= SEQUENCE (SIZE(1..maxnoofMultiConnectivityMinusOne)) OF AdditionalDLUPTNLInformationForHOItem
AdditionalDLUPTNLInformationForHOItem ::= SEQUENCE {
additionalDL-NGU-UP-TNLInformation UPTransportLayerInformation,
additionalQosFlowSetupResponseList QosFlowListWithDataForwarding,
additionalDLForwardingUPTNLInformation UPTransportLayerInformation OPTIONAL,
iE-Extensions ProtocolExtensionContainer { { AdditionalDLUPTNLInformationForHOItem-ExtIEs} } OPTIONAL,
...
}
AdditionalDLUPTNLInformationForHOItem-ExtIEs NGAP-PROTOCOL-EXTENSION ::= {
...
}
AdditionalQosFlowInformation ::= ENUMERATED {
more-likely,
...
}
AllocationAndRetentionPriority ::= SEQUENCE {
priorityLevelARP PriorityLevelARP,
pre-emptionCapability Pre-emptionCapability,
pre-emptionVulnerability Pre-emptionVulnerability,
iE-Extensions ProtocolExtensionContainer { {AllocationAndRetentionPriority-ExtIEs} } OPTIONAL,
...
}
AllocationAndRetentionPriority-ExtIEs NGAP-PROTOCOL-EXTENSION ::= {
...
}
AllowedNSSAI ::= SEQUENCE (SIZE(1..maxnoofAllowedS-NSSAIs)) OF AllowedNSSAI-Item
AllowedNSSAI-Item ::= SEQUENCE {
s-NSSAI S-NSSAI,
iE-Extensions ProtocolExtensionContainer { {AllowedNSSAI-Item-ExtIEs} } OPTIONAL,
...
}
AllowedNSSAI-Item-ExtIEs NGAP-PROTOCOL-EXTENSION ::= {
...
}
AllowedTACs ::= SEQUENCE (SIZE(1..maxnoofAllowedAreas)) OF TAC
AMFName ::= PrintableString (SIZE(1..150, ...))
AMFPagingTarget ::= CHOICE {
globalRANNodeID GlobalRANNodeID,
tAI TAI,
choice-Extensions ProtocolIE-SingleContainer { {AMFPagingTarget-ExtIEs} }
}
AMFPagingTarget-ExtIEs NGAP-PROTOCOL-IES ::= {
...
}
AMFPointer ::= BIT STRING (SIZE(6))
AMFRegionID ::= BIT STRING (SIZE(8))
AMFSetID ::= BIT STRING (SIZE(10))
AMF-TNLAssociationSetupList ::= SEQUENCE (SIZE(1..maxnoofTNLAssociations)) OF AMF-TNLAssociationSetupItem
AMF-TNLAssociationSetupItem ::= SEQUENCE {
aMF-TNLAssociationAddress CPTransportLayerInformation,
iE-Extensions ProtocolExtensionContainer { {AMF-TNLAssociationSetupItem-ExtIEs} } OPTIONAL,
...
}
AMF-TNLAssociationSetupItem-ExtIEs NGAP-PROTOCOL-EXTENSION ::= {
...
}
AMF-TNLAssociationToAddList ::= SEQUENCE (SIZE(1..maxnoofTNLAssociations)) OF AMF-TNLAssociationToAddItem
AMF-TNLAssociationToAddItem ::= SEQUENCE {
aMF-TNLAssociationAddress CPTransportLayerInformation,
tNLAssociationUsage TNLAssociationUsage OPTIONAL,
tNLAddressWeightFactor TNLAddressWeightFactor,
iE-Extensions ProtocolExtensionContainer { {AMF-TNLAssociationToAddItem-ExtIEs} } OPTIONAL,
...
}
AMF-TNLAssociationToAddItem-ExtIEs NGAP-PROTOCOL-EXTENSION ::= {
...
}
AMF-TNLAssociationToRemoveList ::= SEQUENCE (SIZE(1..maxnoofTNLAssociations)) OF AMF-TNLAssociationToRemoveItem
AMF-TNLAssociationToRemoveItem ::= SEQUENCE {
aMF-TNLAssociationAddress CPTransportLayerInformation,
iE-Extensions ProtocolExtensionContainer { {AMF-TNLAssociationToRemoveItem-ExtIEs} } OPTIONAL,
...
}
AMF-TNLAssociationToRemoveItem-ExtIEs NGAP-PROTOCOL-EXTENSION ::= {
{ID id-TNLAssociationTransportLayerAddressNGRAN CRITICALITY reject EXTENSION CPTransportLayerInformation PRESENCE optional},
...
}
AMF-TNLAssociationToUpdateList ::= SEQUENCE (SIZE(1..maxnoofTNLAssociations)) OF AMF-TNLAssociationToUpdateItem
AMF-TNLAssociationToUpdateItem ::= SEQUENCE {
aMF-TNLAssociationAddress CPTransportLayerInformation,
tNLAssociationUsage TNLAssociationUsage OPTIONAL,
tNLAddressWeightFactor TNLAddressWeightFactor OPTIONAL,
iE-Extensions ProtocolExtensionContainer { {AMF-TNLAssociationToUpdateItem-ExtIEs} } OPTIONAL,
...
}
AMF-TNLAssociationToUpdateItem-ExtIEs NGAP-PROTOCOL-EXTENSION ::= {
...
}
AMF-UE-NGAP-ID ::= INTEGER (0..1099511627775)
AreaOfInterest ::= SEQUENCE {
areaOfInterestTAIList AreaOfInterestTAIList OPTIONAL,
areaOfInterestCellList AreaOfInterestCellList OPTIONAL,
areaOfInterestRANNodeList AreaOfInterestRANNodeList OPTIONAL,
iE-Extensions ProtocolExtensionContainer { {AreaOfInterest-ExtIEs} } OPTIONAL,
...
}
AreaOfInterest-ExtIEs NGAP-PROTOCOL-EXTENSION ::= {
...
}
AreaOfInterestCellList ::= SEQUENCE (SIZE(1..maxnoofCellinAoI)) OF AreaOfInterestCellItem
AreaOfInterestCellItem ::= SEQUENCE {
nGRAN-CGI NGRAN-CGI,
iE-Extensions ProtocolExtensionContainer { {AreaOfInterestCellItem-ExtIEs} } OPTIONAL,
...
}
AreaOfInterestCellItem-ExtIEs NGAP-PROTOCOL-EXTENSION ::= {
...
}
AreaOfInterestList ::= SEQUENCE (SIZE(1..maxnoofAoI)) OF AreaOfInterestItem
AreaOfInterestItem ::= SEQUENCE {
areaOfInterest AreaOfInterest,
locationReportingReferenceID LocationReportingReferenceID,
iE-Extensions ProtocolExtensionContainer { {AreaOfInterestItem-ExtIEs} } OPTIONAL,
...
}
AreaOfInterestItem-ExtIEs NGAP-PROTOCOL-EXTENSION ::= {
...
}
AreaOfInterestRANNodeList ::= SEQUENCE (SIZE(1..maxnoofRANNodeinAoI)) OF AreaOfInterestRANNodeItem
AreaOfInterestRANNodeItem ::= SEQUENCE {
globalRANNodeID GlobalRANNodeID,
iE-Extensions ProtocolExtensionContainer { {AreaOfInterestRANNodeItem-ExtIEs} } OPTIONAL,
...
}
AreaOfInterestRANNodeItem-ExtIEs NGAP-PROTOCOL-EXTENSION ::= {
...
}
AreaOfInterestTAIList ::= SEQUENCE (SIZE(1..maxnoofTAIinAoI)) OF AreaOfInterestTAIItem
AreaOfInterestTAIItem ::= SEQUENCE {
tAI TAI,
iE-Extensions ProtocolExtensionContainer { {AreaOfInterestTAIItem-ExtIEs} } OPTIONAL,
...
}
AreaOfInterestTAIItem-ExtIEs NGAP-PROTOCOL-EXTENSION ::= {
...
}
AssistanceDataForPaging ::= SEQUENCE {
assistanceDataForRecommendedCells AssistanceDataForRecommendedCells OPTIONAL,
pagingAttemptInformation PagingAttemptInformation OPTIONAL,
iE-Extensions ProtocolExtensionContainer { {AssistanceDataForPaging-ExtIEs} } OPTIONAL,
...
}
AssistanceDataForPaging-ExtIEs NGAP-PROTOCOL-EXTENSION ::= {
...
}
AssistanceDataForRecommendedCells ::= SEQUENCE {
recommendedCellsForPaging RecommendedCellsForPaging,
iE-Extensions ProtocolExtensionContainer { {AssistanceDataForRecommendedCells-ExtIEs} } OPTIONAL,
...
}
AssistanceDataForRecommendedCells-ExtIEs NGAP-PROTOCOL-EXTENSION ::= {
...
}
AssociatedQosFlowList ::= SEQUENCE (SIZE(1..maxnoofQosFlows)) OF AssociatedQosFlowItem
AssociatedQosFlowItem ::= SEQUENCE {
qosFlowIdentifier QosFlowIdentifier,
qosFlowMappingIndication ENUMERATED {ul, dl, ...} OPTIONAL,
iE-Extensions ProtocolExtensionContainer { {AssociatedQosFlowItem-ExtIEs} } OPTIONAL,
...
}
AssociatedQosFlowItem-ExtIEs NGAP-PROTOCOL-EXTENSION ::= {
...
}
AveragingWindow ::= INTEGER (0..4095, ...)
-- B
BitRate ::= INTEGER (0..4000000000000, ...)
BroadcastCancelledAreaList ::= CHOICE {
cellIDCancelledEUTRA CellIDCancelledEUTRA,
tAICancelledEUTRA TAICancelledEUTRA,
emergencyAreaIDCancelledEUTRA EmergencyAreaIDCancelledEUTRA,
cellIDCancelledNR CellIDCancelledNR,
tAICancelledNR TAICancelledNR,
emergencyAreaIDCancelledNR EmergencyAreaIDCancelledNR,
choice-Extensions ProtocolIE-SingleContainer { {BroadcastCancelledAreaList-ExtIEs} }
}
BroadcastCancelledAreaList-ExtIEs NGAP-PROTOCOL-IES ::= {
...
}
BroadcastCompletedAreaList ::= CHOICE {
cellIDBroadcastEUTRA CellIDBroadcastEUTRA,
tAIBroadcastEUTRA TAIBroadcastEUTRA,
emergencyAreaIDBroadcastEUTRA EmergencyAreaIDBroadcastEUTRA,
cellIDBroadcastNR CellIDBroadcastNR,
tAIBroadcastNR TAIBroadcastNR,
emergencyAreaIDBroadcastNR EmergencyAreaIDBroadcastNR,
choice-Extensions ProtocolIE-SingleContainer { {BroadcastCompletedAreaList-ExtIEs} }
}
BroadcastCompletedAreaList-ExtIEs NGAP-PROTOCOL-IES ::= {
...
}
BroadcastPLMNList ::= SEQUENCE (SIZE(1..maxnoofBPLMNs)) OF BroadcastPLMNItem
BroadcastPLMNItem ::= SEQUENCE {
pLMNIdentity PLMNIdentity,
tAISliceSupportList SliceSupportList,
iE-Extensions ProtocolExtensionContainer { {BroadcastPLMNItem-ExtIEs} } OPTIONAL,
...
}
BroadcastPLMNItem-ExtIEs NGAP-PROTOCOL-EXTENSION ::= {
...
}
-- C
CancelAllWarningMessages ::= ENUMERATED {
true,
...
}
CancelledCellsInEAI-EUTRA ::= SEQUENCE (SIZE(1..maxnoofCellinEAI)) OF CancelledCellsInEAI-EUTRA-Item
CancelledCellsInEAI-EUTRA-Item ::= SEQUENCE {
eUTRA-CGI EUTRA-CGI,
numberOfBroadcasts NumberOfBroadcasts,
iE-Extensions ProtocolExtensionContainer { {CancelledCellsInEAI-EUTRA-Item-ExtIEs} } OPTIONAL,
...
}
CancelledCellsInEAI-EUTRA-Item-ExtIEs NGAP-PROTOCOL-EXTENSION ::= {
...
}
CancelledCellsInEAI-NR ::= SEQUENCE (SIZE(1..maxnoofCellinEAI)) OF CancelledCellsInEAI-NR-Item
CancelledCellsInEAI-NR-Item ::= SEQUENCE {
nR-CGI NR-CGI,
numberOfBroadcasts NumberOfBroadcasts,
iE-Extensions ProtocolExtensionContainer { {CancelledCellsInEAI-NR-Item-ExtIEs} } OPTIONAL,
...
}
CancelledCellsInEAI-NR-Item-ExtIEs NGAP-PROTOCOL-EXTENSION ::= {
...
}
CancelledCellsInTAI-EUTRA ::= SEQUENCE (SIZE(1..maxnoofCellinTAI)) OF CancelledCellsInTAI-EUTRA-Item
CancelledCellsInTAI-EUTRA-Item ::= SEQUENCE {
eUTRA-CGI EUTRA-CGI,
numberOfBroadcasts NumberOfBroadcasts,
iE-Extensions ProtocolExtensionContainer { {CancelledCellsInTAI-EUTRA-Item-ExtIEs} } OPTIONAL,
...
}
CancelledCellsInTAI-EUTRA-Item-ExtIEs NGAP-PROTOCOL-EXTENSION ::= {
...
}
CancelledCellsInTAI-NR ::= SEQUENCE (SIZE(1..maxnoofCellinTAI)) OF CancelledCellsInTAI-NR-Item
CancelledCellsInTAI-NR-Item ::= SEQUENCE{
nR-CGI NR-CGI,
numberOfBroadcasts NumberOfBroadcasts,
iE-Extensions ProtocolExtensionContainer { {CancelledCellsInTAI-NR-Item-ExtIEs} } OPTIONAL,
...
}
CancelledCellsInTAI-NR-Item-ExtIEs NGAP-PROTOCOL-EXTENSION ::= {
...
}
Cause ::= CHOICE {
radioNetwork CauseRadioNetwork,
transport CauseTransport,
nas CauseNas,
protocol CauseProtocol,
misc CauseMisc,
choice-Extensions ProtocolIE-SingleContainer { {Cause-ExtIEs} }
}
Cause-ExtIEs NGAP-PROTOCOL-IES ::= {
...
}
CauseMisc ::= ENUMERATED {
control-processing-overload,
not-enough-user-plane-processing-resources,
hardware-failure,
om-intervention,
unknown-PLMN,
unspecified,
...
}
CauseNas ::= ENUMERATED {
normal-release,
authentication-failure,
deregister,
unspecified,
...
}
CauseProtocol ::= ENUMERATED {
transfer-syntax-error,
abstract-syntax-error-reject,
abstract-syntax-error-ignore-and-notify,
message-not-compatible-with-receiver-state,
semantic-error,
abstract-syntax-error-falsely-constructed-message,
unspecified,
...
}
CauseRadioNetwork ::= ENUMERATED {
unspecified,
txnrelocoverall-expiry,
successful-handover,
release-due-to-ngran-generated-reason,
release-due-to-5gc-generated-reason,
handover-cancelled,
partial-handover,
ho-failure-in-target-5GC-ngran-node-or-target-system,
ho-target-not-allowed,
tngrelocoverall-expiry,
tngrelocprep-expiry,
cell-not-available,
unknown-targetID,
no-radio-resources-available-in-target-cell,
unknown-local-UE-NGAP-ID,
inconsistent-remote-UE-NGAP-ID,
handover-desirable-for-radio-reason,
time-critical-handover,
resource-optimisation-handover,
reduce-load-in-serving-cell,
user-inactivity,
radio-connection-with-ue-lost,
radio-resources-not-available,
invalid-qos-combination,
failure-in-radio-interface-procedure,
interaction-with-other-procedure,
unknown-PDU-session-ID,
unkown-qos-flow-ID,
multiple-PDU-session-ID-instances,
multiple-qos-flow-ID-instances,
encryption-and-or-integrity-protection-algorithms-not-supported,
ng-intra-system-handover-triggered,
ng-inter-system-handover-triggered,
xn-handover-triggered,
not-supported-5QI-value,
ue-context-transfer,
ims-voice-eps-fallback-or-rat-fallback-triggered,
up-integrity-protection-not-possible,
up-confidentiality-protection-not-possible,
slice-not-supported,
ue-in-rrc-inactive-state-not-reachable,
redirection,
resources-not-available-for-the-slice,
ue-max-integrity-protected-data-rate-reason,
release-due-to-cn-detected-mobility,
...,
n26-interface-not-available,
release-due-to-pre-emption,
multiple-location-reporting-reference-ID-instances
}
CauseTransport ::= ENUMERATED {
transport-resource-unavailable,
unspecified,
...
}
CellIDBroadcastEUTRA ::= SEQUENCE (SIZE(1..maxnoofCellIDforWarning)) OF CellIDBroadcastEUTRA-Item
CellIDBroadcastEUTRA-Item ::= SEQUENCE {
eUTRA-CGI EUTRA-CGI,
iE-Extensions ProtocolExtensionContainer { {CellIDBroadcastEUTRA-Item-ExtIEs} } OPTIONAL,
...
}
CellIDBroadcastEUTRA-Item-ExtIEs NGAP-PROTOCOL-EXTENSION ::= {
...
}
CellIDBroadcastNR ::= SEQUENCE (SIZE(1..maxnoofCellIDforWarning)) OF CellIDBroadcastNR-Item
CellIDBroadcastNR-Item ::= SEQUENCE {
nR-CGI NR-CGI,
iE-Extensions ProtocolExtensionContainer { {CellIDBroadcastNR-Item-ExtIEs} } OPTIONAL,
...
}
CellIDBroadcastNR-Item-ExtIEs NGAP-PROTOCOL-EXTENSION ::= {
...
}
CellIDCancelledEUTRA ::= SEQUENCE (SIZE(1..maxnoofCellIDforWarning)) OF CellIDCancelledEUTRA-Item
CellIDCancelledEUTRA-Item ::= SEQUENCE {
eUTRA-CGI EUTRA-CGI,
numberOfBroadcasts NumberOfBroadcasts,
iE-Extensions ProtocolExtensionContainer { {CellIDCancelledEUTRA-Item-ExtIEs} } OPTIONAL,
...
}
CellIDCancelledEUTRA-Item-ExtIEs NGAP-PROTOCOL-EXTENSION ::= {
...
}
CellIDCancelledNR ::= SEQUENCE (SIZE(1..maxnoofCellIDforWarning)) OF CellIDCancelledNR-Item
CellIDCancelledNR-Item ::= SEQUENCE {
nR-CGI NR-CGI,
numberOfBroadcasts NumberOfBroadcasts,
iE-Extensions ProtocolExtensionContainer { {CellIDCancelledNR-Item-ExtIEs} } OPTIONAL,
...
}
CellIDCancelledNR-Item-ExtIEs NGAP-PROTOCOL-EXTENSION ::= {
...
}
CellIDListForRestart ::= CHOICE {
eUTRA-CGIListforRestart EUTRA-CGIList,
nR-CGIListforRestart NR-CGIList,
choice-Extensions ProtocolIE-SingleContainer { {CellIDListForRestart-ExtIEs} }
}
CellIDListForRestart-ExtIEs NGAP-PROTOCOL-IES ::= {
...
}
CellSize ::= ENUMERATED {verysmall, small, medium, large, ...}
CellType ::= SEQUENCE {
cellSize CellSize,
iE-Extensions ProtocolExtensionContainer { {CellType-ExtIEs} } OPTIONAL,
...
}
CellType-ExtIEs NGAP-PROTOCOL-EXTENSION ::= {
...
}
CNAssistedRANTuning ::= SEQUENCE {
expectedUEBehaviour ExpectedUEBehaviour OPTIONAL,
iE-Extensions ProtocolExtensionContainer { {CNAssistedRANTuning-ExtIEs} } OPTIONAL,
...
}
CNAssistedRANTuning-ExtIEs NGAP-PROTOCOL-EXTENSION ::= {
...
}
CNTypeRestrictionsForEquivalent ::= SEQUENCE (SIZE(1..maxnoofEPLMNs)) OF CNTypeRestrictionsForEquivalentItem
CNTypeRestrictionsForEquivalentItem ::= SEQUENCE {
plmnIdentity PLMNIdentity,
cn-Type ENUMERATED {epc-forbidden, fiveGC-forbidden, ...},
iE-Extensions ProtocolExtensionContainer { {CNTypeRestrictionsForEquivalentItem-ExtIEs} } OPTIONAL,
...
}
CNTypeRestrictionsForEquivalentItem-ExtIEs NGAP-PROTOCOL-EXTENSION ::={
...
}
CNTypeRestrictionsForServing ::= ENUMERATED {
epc-forbidden,
...
}
CommonNetworkInstance ::= OCTET STRING
CompletedCellsInEAI-EUTRA ::= SEQUENCE (SIZE(1..maxnoofCellinEAI)) OF CompletedCellsInEAI-EUTRA-Item
CompletedCellsInEAI-EUTRA-Item ::= SEQUENCE {
eUTRA-CGI EUTRA-CGI,
iE-Extensions ProtocolExtensionContainer { {CompletedCellsInEAI-EUTRA-Item-ExtIEs} } OPTIONAL,
...
}
CompletedCellsInEAI-EUTRA-Item-ExtIEs NGAP-PROTOCOL-EXTENSION ::= {
...
}
CompletedCellsInEAI-NR ::= SEQUENCE (SIZE(1..maxnoofCellinEAI)) OF CompletedCellsInEAI-NR-Item
CompletedCellsInEAI-NR-Item ::= SEQUENCE {
nR-CGI NR-CGI,
iE-Extensions ProtocolExtensionContainer { {CompletedCellsInEAI-NR-Item-ExtIEs} } OPTIONAL,
...
}
CompletedCellsInEAI-NR-Item-ExtIEs NGAP-PROTOCOL-EXTENSION ::= {
...
}
CompletedCellsInTAI-EUTRA ::= SEQUENCE (SIZE(1..maxnoofCellinTAI)) OF CompletedCellsInTAI-EUTRA-Item
CompletedCellsInTAI-EUTRA-Item ::= SEQUENCE{
eUTRA-CGI EUTRA-CGI,
iE-Extensions ProtocolExtensionContainer { {CompletedCellsInTAI-EUTRA-Item-ExtIEs} } OPTIONAL,
...
}
CompletedCellsInTAI-EUTRA-Item-ExtIEs NGAP-PROTOCOL-EXTENSION ::= {
...
}
CompletedCellsInTAI-NR ::= SEQUENCE (SIZE(1..maxnoofCellinTAI)) OF CompletedCellsInTAI-NR-Item
CompletedCellsInTAI-NR-Item ::= SEQUENCE{
nR-CGI NR-CGI,
iE-Extensions ProtocolExtensionContainer { {CompletedCellsInTAI-NR-Item-ExtIEs} } OPTIONAL,
...
}
CompletedCellsInTAI-NR-Item-ExtIEs NGAP-PROTOCOL-EXTENSION ::= {
...
}
ConcurrentWarningMessageInd ::= ENUMERATED {
true,
...
}
ConfidentialityProtectionIndication ::= ENUMERATED {
required,
preferred,
not-needed,
...
}
ConfidentialityProtectionResult ::= ENUMERATED {
performed,
not-performed,
...
}
CoreNetworkAssistanceInformationForInactive ::= SEQUENCE {
uEIdentityIndexValue UEIdentityIndexValue,
uESpecificDRX PagingDRX OPTIONAL,
periodicRegistrationUpdateTimer PeriodicRegistrationUpdateTimer,
mICOModeIndication MICOModeIndication OPTIONAL,
tAIListForInactive TAIListForInactive,
expectedUEBehaviour ExpectedUEBehaviour OPTIONAL,
iE-Extensions ProtocolExtensionContainer { {CoreNetworkAssistanceInformationForInactive-ExtIEs} } OPTIONAL,
...
}
CoreNetworkAssistanceInformationForInactive-ExtIEs NGAP-PROTOCOL-EXTENSION ::= {
...
}
COUNTValueForPDCP-SN12 ::= SEQUENCE {
pDCP-SN12 INTEGER (0..4095),
hFN-PDCP-SN12 INTEGER (0..1048575),
iE-Extensions ProtocolExtensionContainer { {COUNTValueForPDCP-SN12-ExtIEs} } OPTIONAL,
...
}
COUNTValueForPDCP-SN12-ExtIEs NGAP-PROTOCOL-EXTENSION ::= {
...
}
COUNTValueForPDCP-SN18 ::= SEQUENCE {
pDCP-SN18 INTEGER (0..262143),
hFN-PDCP-SN18 INTEGER (0..16383),
iE-Extensions ProtocolExtensionContainer { {COUNTValueForPDCP-SN18-ExtIEs} } OPTIONAL,
...
}
COUNTValueForPDCP-SN18-ExtIEs NGAP-PROTOCOL-EXTENSION ::= {
...
}
CPTransportLayerInformation ::= CHOICE {
endpointIPAddress TransportLayerAddress,
choice-Extensions ProtocolIE-SingleContainer { {CPTransportLayerInformation-ExtIEs} }
}
CPTransportLayerInformation-ExtIEs NGAP-PROTOCOL-IES ::= {
{ ID id-EndpointIPAddressAndPort CRITICALITY reject TYPE EndpointIPAddressAndPort PRESENCE mandatory},
...
}
CriticalityDiagnostics ::= SEQUENCE {
procedureCode ProcedureCode OPTIONAL,
triggeringMessage TriggeringMessage OPTIONAL,
procedureCriticality Criticality OPTIONAL,
iEsCriticalityDiagnostics CriticalityDiagnostics-IE-List OPTIONAL,
iE-Extensions ProtocolExtensionContainer {{CriticalityDiagnostics-ExtIEs}} OPTIONAL,
...
}
CriticalityDiagnostics-ExtIEs NGAP-PROTOCOL-EXTENSION ::= {
...
}
CriticalityDiagnostics-IE-List ::= SEQUENCE (SIZE(1..maxnoofErrors)) OF CriticalityDiagnostics-IE-Item
CriticalityDiagnostics-IE-Item ::= SEQUENCE {
iECriticality Criticality,
iE-ID ProtocolIE-ID,
typeOfError TypeOfError,
iE-Extensions ProtocolExtensionContainer {{CriticalityDiagnostics-IE-Item-ExtIEs}} OPTIONAL,
...
}
CriticalityDiagnostics-IE-Item-ExtIEs NGAP-PROTOCOL-EXTENSION ::= {
...
}
-- D
DataCodingScheme ::= BIT STRING (SIZE(8))
DataForwardingAccepted ::= ENUMERATED {
data-forwarding-accepted,
...
}
DataForwardingNotPossible ::= ENUMERATED {
data-forwarding-not-possible,
...
}
DataForwardingResponseDRBList ::= SEQUENCE (SIZE(1..maxnoofDRBs)) OF DataForwardingResponseDRBItem
DataForwardingResponseDRBItem ::= SEQUENCE {
dRB-ID DRB-ID,
dLForwardingUP-TNLInformation UPTransportLayerInformation OPTIONAL,
uLForwardingUP-TNLInformation UPTransportLayerInformation OPTIONAL,
iE-Extensions ProtocolExtensionContainer {{DataForwardingResponseDRBItem-ExtIEs}} OPTIONAL,
...
}
DataForwardingResponseDRBItem-ExtIEs NGAP-PROTOCOL-EXTENSION ::= {
...
}
DelayCritical ::= ENUMERATED {
delay-critical,
non-delay-critical,
...
}
DLForwarding ::= ENUMERATED {
dl-forwarding-proposed,
...
}
DL-NGU-TNLInformationReused ::= ENUMERATED {
true,
...
}
DirectForwardingPathAvailability ::= ENUMERATED {
direct-path-available,
...
}
DRB-ID ::= INTEGER (1..32, ...)
DRBsSubjectToStatusTransferList ::= SEQUENCE (SIZE(1..maxnoofDRBs)) OF DRBsSubjectToStatusTransferItem
DRBsSubjectToStatusTransferItem ::= SEQUENCE {
dRB-ID DRB-ID,
dRBStatusUL DRBStatusUL,
dRBStatusDL DRBStatusDL,
iE-Extension ProtocolExtensionContainer { {DRBsSubjectToStatusTransferItem-ExtIEs} } OPTIONAL,
...
}
DRBsSubjectToStatusTransferItem-ExtIEs NGAP-PROTOCOL-EXTENSION ::= {
{ ID id-OldAssociatedQosFlowList-ULendmarkerexpected CRITICALITY reject EXTENSION AssociatedQosFlowList PRESENCE optional },
...
}
DRBStatusDL ::= CHOICE {
dRBStatusDL12 DRBStatusDL12,
dRBStatusDL18 DRBStatusDL18,
choice-Extensions ProtocolIE-SingleContainer { {DRBStatusDL-ExtIEs} }
}
DRBStatusDL-ExtIEs NGAP-PROTOCOL-IES ::= {
...
}
DRBStatusDL12 ::= SEQUENCE {
dL-COUNTValue COUNTValueForPDCP-SN12,
iE-Extension ProtocolExtensionContainer { {DRBStatusDL12-ExtIEs} } OPTIONAL,
...
}
DRBStatusDL12-ExtIEs NGAP-PROTOCOL-EXTENSION ::= {
...
}
DRBStatusDL18 ::= SEQUENCE {
dL-COUNTValue COUNTValueForPDCP-SN18,
iE-Extension ProtocolExtensionContainer { {DRBStatusDL18-ExtIEs} } OPTIONAL,
...
}
DRBStatusDL18-ExtIEs NGAP-PROTOCOL-EXTENSION ::= {
...
}
DRBStatusUL ::= CHOICE {
dRBStatusUL12 DRBStatusUL12,
dRBStatusUL18 DRBStatusUL18,
choice-Extensions ProtocolIE-SingleContainer { {DRBStatusUL-ExtIEs} }
}
DRBStatusUL-ExtIEs NGAP-PROTOCOL-IES ::= {
...
}
DRBStatusUL12 ::= SEQUENCE {
uL-COUNTValue COUNTValueForPDCP-SN12,
receiveStatusOfUL-PDCP-SDUs BIT STRING (SIZE(1..2048)) OPTIONAL,
iE-Extension ProtocolExtensionContainer { {DRBStatusUL12-ExtIEs} } OPTIONAL,
...
}
DRBStatusUL12-ExtIEs NGAP-PROTOCOL-EXTENSION ::= {
...
}
DRBStatusUL18 ::= SEQUENCE {
uL-COUNTValue COUNTValueForPDCP-SN18,
receiveStatusOfUL-PDCP-SDUs BIT STRING (SIZE(1..131072)) OPTIONAL,
iE-Extension ProtocolExtensionContainer { {DRBStatusUL18-ExtIEs} } OPTIONAL,
...
}
DRBStatusUL18-ExtIEs NGAP-PROTOCOL-EXTENSION ::= {
...
}
DRBsToQosFlowsMappingList ::= SEQUENCE (SIZE(1..maxnoofDRBs)) OF DRBsToQosFlowsMappingItem
DRBsToQosFlowsMappingItem ::= SEQUENCE {
dRB-ID DRB-ID,
associatedQosFlowList AssociatedQosFlowList,
iE-Extensions ProtocolExtensionContainer { {DRBsToQosFlowsMappingItem-ExtIEs} } OPTIONAL,
...
}
DRBsToQosFlowsMappingItem-ExtIEs NGAP-PROTOCOL-EXTENSION ::= {
...
}
Dynamic5QIDescriptor ::= SEQUENCE {
priorityLevelQos PriorityLevelQos,
packetDelayBudget PacketDelayBudget,
packetErrorRate PacketErrorRate,
fiveQI FiveQI OPTIONAL,
delayCritical DelayCritical OPTIONAL,
-- The above IE shall be present in case of GBR QoS flow
averagingWindow AveragingWindow OPTIONAL,
-- The above IE shall be present in case of GBR QoS flow
maximumDataBurstVolume MaximumDataBurstVolume OPTIONAL,
iE-Extensions ProtocolExtensionContainer { {Dynamic5QIDescriptor-ExtIEs} } OPTIONAL,
...
}
Dynamic5QIDescriptor-ExtIEs NGAP-PROTOCOL-EXTENSION ::= {
...
}
-- E
EmergencyAreaID ::= OCTET STRING (SIZE(3))
EmergencyAreaIDBroadcastEUTRA ::= SEQUENCE (SIZE(1..maxnoofEmergencyAreaID)) OF EmergencyAreaIDBroadcastEUTRA-Item
EmergencyAreaIDBroadcastEUTRA-Item ::= SEQUENCE {
emergencyAreaID EmergencyAreaID,
completedCellsInEAI-EUTRA CompletedCellsInEAI-EUTRA,
iE-Extensions ProtocolExtensionContainer { {EmergencyAreaIDBroadcastEUTRA-Item-ExtIEs} } OPTIONAL,
...
}
EmergencyAreaIDBroadcastEUTRA-Item-ExtIEs NGAP-PROTOCOL-EXTENSION ::= {
...
}
EmergencyAreaIDBroadcastNR ::= SEQUENCE (SIZE(1..maxnoofEmergencyAreaID)) OF EmergencyAreaIDBroadcastNR-Item
EmergencyAreaIDBroadcastNR-Item ::= SEQUENCE {
emergencyAreaID EmergencyAreaID,
completedCellsInEAI-NR CompletedCellsInEAI-NR,
iE-Extensions ProtocolExtensionContainer { {EmergencyAreaIDBroadcastNR-Item-ExtIEs} } OPTIONAL,
...
}
EmergencyAreaIDBroadcastNR-Item-ExtIEs NGAP-PROTOCOL-EXTENSION ::= {
...
}
EmergencyAreaIDCancelledEUTRA ::= SEQUENCE (SIZE(1..maxnoofEmergencyAreaID)) OF EmergencyAreaIDCancelledEUTRA-Item
EmergencyAreaIDCancelledEUTRA-Item ::= SEQUENCE {
emergencyAreaID EmergencyAreaID,
cancelledCellsInEAI-EUTRA CancelledCellsInEAI-EUTRA,
iE-Extensions ProtocolExtensionContainer { {EmergencyAreaIDCancelledEUTRA-Item-ExtIEs} } OPTIONAL,
...
}
EmergencyAreaIDCancelledEUTRA-Item-ExtIEs NGAP-PROTOCOL-EXTENSION ::= {
...
}
EmergencyAreaIDCancelledNR ::= SEQUENCE (SIZE(1..maxnoofEmergencyAreaID)) OF EmergencyAreaIDCancelledNR-Item
EmergencyAreaIDCancelledNR-Item ::= SEQUENCE {
emergencyAreaID EmergencyAreaID,
cancelledCellsInEAI-NR CancelledCellsInEAI-NR,
iE-Extensions ProtocolExtensionContainer { {EmergencyAreaIDCancelledNR-Item-ExtIEs} } OPTIONAL,
...
}
EmergencyAreaIDCancelledNR-Item-ExtIEs NGAP-PROTOCOL-EXTENSION ::= {
...
}
EmergencyAreaIDList ::= SEQUENCE (SIZE(1..maxnoofEmergencyAreaID)) OF EmergencyAreaID
EmergencyAreaIDListForRestart ::= SEQUENCE (SIZE(1..maxnoofEAIforRestart)) OF EmergencyAreaID
EmergencyFallbackIndicator ::= SEQUENCE {
emergencyFallbackRequestIndicator EmergencyFallbackRequestIndicator,
emergencyServiceTargetCN EmergencyServiceTargetCN OPTIONAL,
iE-Extensions ProtocolExtensionContainer { {EmergencyFallbackIndicator-ExtIEs} } OPTIONAL,
...
}
EmergencyFallbackIndicator-ExtIEs NGAP-PROTOCOL-EXTENSION ::= {
...
}
EmergencyFallbackRequestIndicator ::= ENUMERATED {
emergency-fallback-requested,
...
}
EmergencyServiceTargetCN ::= ENUMERATED {
fiveGC,
epc,
...
}
EN-DCSONConfigurationTransfer ::= OCTET STRING
EndpointIPAddressAndPort ::=SEQUENCE {
endpointIPAddress TransportLayerAddress,
portNumber PortNumber,
iE-Extensions ProtocolExtensionContainer { { EndpointIPAddressAndPort-ExtIEs} } OPTIONAL
}
EndpointIPAddressAndPort-ExtIEs NGAP-PROTOCOL-EXTENSION ::= {
...
}
EquivalentPLMNs ::= SEQUENCE (SIZE(1..maxnoofEPLMNs)) OF PLMNIdentity
EPS-TAC ::= OCTET STRING (SIZE(2))
EPS-TAI ::= SEQUENCE {
pLMNIdentity PLMNIdentity,
ePS-TAC EPS-TAC,
iE-Extensions ProtocolExtensionContainer { {EPS-TAI-ExtIEs} } OPTIONAL,
...
}
EPS-TAI-ExtIEs NGAP-PROTOCOL-EXTENSION ::= {
...
}
E-RAB-ID ::= INTEGER (0..15, ...)
E-RABInformationList ::= SEQUENCE (SIZE(1..maxnoofE-RABs)) OF E-RABInformationItem
E-RABInformationItem ::= SEQUENCE {
e-RAB-ID E-RAB-ID,
dLForwarding DLForwarding OPTIONAL,
iE-Extensions ProtocolExtensionContainer { {E-RABInformationItem-ExtIEs} } OPTIONAL,
...
}
E-RABInformationItem-ExtIEs NGAP-PROTOCOL-EXTENSION ::= {
...
}
EUTRACellIdentity ::= BIT STRING (SIZE(28))
EUTRA-CGI ::= SEQUENCE {
pLMNIdentity PLMNIdentity,
eUTRACellIdentity EUTRACellIdentity,
iE-Extensions ProtocolExtensionContainer { {EUTRA-CGI-ExtIEs} } OPTIONAL,
...
}
EUTRA-CGI-ExtIEs NGAP-PROTOCOL-EXTENSION ::= {
...
}
EUTRA-CGIList ::= SEQUENCE (SIZE(1..maxnoofCellsinngeNB)) OF EUTRA-CGI
EUTRA-CGIListForWarning ::= SEQUENCE (SIZE(1..maxnoofCellIDforWarning)) OF EUTRA-CGI
EUTRAencryptionAlgorithms ::= BIT STRING (SIZE(16, ...))
EUTRAintegrityProtectionAlgorithms ::= BIT STRING (SIZE(16, ...))
EventType ::= ENUMERATED {
direct,
change-of-serve-cell,
ue-presence-in-area-of-interest,
stop-change-of-serve-cell,
stop-ue-presence-in-area-of-interest,
cancel-location-reporting-for-the-ue,
...
}
ExpectedActivityPeriod ::= INTEGER (1..30|40|50|60|80|100|120|150|180|181, ...)
ExpectedHOInterval ::= ENUMERATED {
sec15, sec30, sec60, sec90, sec120, sec180, long-time,
...
}
ExpectedIdlePeriod ::= INTEGER (1..30|40|50|60|80|100|120|150|180|181, ...)
ExpectedUEActivityBehaviour ::= SEQUENCE {
expectedActivityPeriod ExpectedActivityPeriod OPTIONAL,
expectedIdlePeriod ExpectedIdlePeriod OPTIONAL,
sourceOfUEActivityBehaviourInformation SourceOfUEActivityBehaviourInformation OPTIONAL,
iE-Extensions ProtocolExtensionContainer { {ExpectedUEActivityBehaviour-ExtIEs} } OPTIONAL,
...
}
ExpectedUEActivityBehaviour-ExtIEs NGAP-PROTOCOL-EXTENSION ::= {
...
}
ExpectedUEBehaviour ::= SEQUENCE {
expectedUEActivityBehaviour ExpectedUEActivityBehaviour OPTIONAL,
expectedHOInterval ExpectedHOInterval OPTIONAL,
expectedUEMobility ExpectedUEMobility OPTIONAL,
expectedUEMovingTrajectory ExpectedUEMovingTrajectory OPTIONAL,
iE-Extensions ProtocolExtensionContainer { {ExpectedUEBehaviour-ExtIEs} } OPTIONAL,
...
}
ExpectedUEBehaviour-ExtIEs NGAP-PROTOCOL-EXTENSION ::= {
...
}
ExpectedUEMobility ::= ENUMERATED {
stationary,
mobile,
...
}
ExpectedUEMovingTrajectory ::= SEQUENCE (SIZE(1..maxnoofCellsUEMovingTrajectory)) OF ExpectedUEMovingTrajectoryItem
ExpectedUEMovingTrajectoryItem ::= SEQUENCE {
nGRAN-CGI NGRAN-CGI,
timeStayedInCell INTEGER (0..4095) OPTIONAL,
iE-Extensions ProtocolExtensionContainer { {ExpectedUEMovingTrajectoryItem-ExtIEs} } OPTIONAL,
...
}
ExpectedUEMovingTrajectoryItem-ExtIEs NGAP-PROTOCOL-EXTENSION ::= {
...
}
-- F
FiveG-S-TMSI ::= SEQUENCE {
aMFSetID AMFSetID,
aMFPointer AMFPointer,
fiveG-TMSI FiveG-TMSI,
iE-Extensions ProtocolExtensionContainer { {FiveG-S-TMSI-ExtIEs} } OPTIONAL,
...
}
FiveG-S-TMSI-ExtIEs NGAP-PROTOCOL-EXTENSION ::= {
...
}
FiveG-TMSI ::= OCTET STRING (SIZE(4))
FiveQI ::= INTEGER (0..255, ...)
ForbiddenAreaInformation ::= SEQUENCE (SIZE(1.. maxnoofEPLMNsPlusOne)) OF ForbiddenAreaInformation-Item
ForbiddenAreaInformation-Item ::= SEQUENCE {
pLMNIdentity PLMNIdentity,
forbiddenTACs ForbiddenTACs,
iE-Extensions ProtocolExtensionContainer { {ForbiddenAreaInformation-Item-ExtIEs} } OPTIONAL,
...
}
ForbiddenAreaInformation-Item-ExtIEs NGAP-PROTOCOL-EXTENSION ::= {
...
}
ForbiddenTACs ::= SEQUENCE (SIZE(1..maxnoofForbTACs)) OF TAC
-- G
GBR-QosInformation ::= SEQUENCE {
maximumFlowBitRateDL BitRate,
maximumFlowBitRateUL BitRate,
guaranteedFlowBitRateDL BitRate,
guaranteedFlowBitRateUL BitRate,
notificationControl NotificationControl OPTIONAL,
maximumPacketLossRateDL PacketLossRate OPTIONAL,
maximumPacketLossRateUL PacketLossRate OPTIONAL,
iE-Extensions ProtocolExtensionContainer { {GBR-QosInformation-ExtIEs} } OPTIONAL,
...
}
GBR-QosInformation-ExtIEs NGAP-PROTOCOL-EXTENSION ::= {
...}
GlobalGNB-ID ::= SEQUENCE {
pLMNIdentity PLMNIdentity,
gNB-ID GNB-ID,
iE-Extensions ProtocolExtensionContainer { {GlobalGNB-ID-ExtIEs} } OPTIONAL,
...
}
GlobalGNB-ID-ExtIEs NGAP-PROTOCOL-EXTENSION ::= {
...
}
GlobalN3IWF-ID ::= SEQUENCE {
pLMNIdentity PLMNIdentity,
n3IWF-ID N3IWF-ID,
iE-Extensions ProtocolExtensionContainer { {GlobalN3IWF-ID-ExtIEs} } OPTIONAL,
...
}
GlobalN3IWF-ID-ExtIEs NGAP-PROTOCOL-EXTENSION ::= {
...
}
GlobalNgENB-ID ::= SEQUENCE {
pLMNIdentity PLMNIdentity,
ngENB-ID NgENB-ID,
iE-Extensions ProtocolExtensionContainer { {GlobalNgENB-ID-ExtIEs} } OPTIONAL,
...
}
GlobalNgENB-ID-ExtIEs NGAP-PROTOCOL-EXTENSION ::= {
...
}
GlobalRANNodeID ::= CHOICE {
globalGNB-ID GlobalGNB-ID,
globalNgENB-ID GlobalNgENB-ID,
globalN3IWF-ID GlobalN3IWF-ID,
choice-Extensions ProtocolIE-SingleContainer { {GlobalRANNodeID-ExtIEs} }
}
GlobalRANNodeID-ExtIEs NGAP-PROTOCOL-IES ::= {
...
}
GNB-ID ::= CHOICE {
gNB-ID BIT STRING (SIZE(22..32)),
choice-Extensions ProtocolIE-SingleContainer { {GNB-ID-ExtIEs} }
}
GNB-ID-ExtIEs NGAP-PROTOCOL-IES ::= {
...
}
GTP-TEID ::= OCTET STRING (SIZE(4))
GTPTunnel ::= SEQUENCE {
transportLayerAddress TransportLayerAddress,
gTP-TEID GTP-TEID,
iE-Extensions ProtocolExtensionContainer { {GTPTunnel-ExtIEs} } OPTIONAL,
...
}
GTPTunnel-ExtIEs NGAP-PROTOCOL-EXTENSION ::= {
...
}
GUAMI ::= SEQUENCE {
pLMNIdentity PLMNIdentity,
aMFRegionID AMFRegionID,
aMFSetID AMFSetID,
aMFPointer AMFPointer,
iE-Extensions ProtocolExtensionContainer { {GUAMI-ExtIEs} } OPTIONAL,
...
}
GUAMI-ExtIEs NGAP-PROTOCOL-EXTENSION ::= {
...
}
-- H
HandoverCommandTransfer ::= SEQUENCE {
dLForwardingUP-TNLInformation UPTransportLayerInformation OPTIONAL,
qosFlowToBeForwardedList QosFlowToBeForwardedList OPTIONAL,
dataForwardingResponseDRBList DataForwardingResponseDRBList OPTIONAL,
iE-Extensions ProtocolExtensionContainer { {HandoverCommandTransfer-ExtIEs} } OPTIONAL,
...
}
HandoverCommandTransfer-ExtIEs NGAP-PROTOCOL-EXTENSION ::= {
{ ID id-AdditionalDLForwardingUPTNLInformation CRITICALITY ignore EXTENSION QosFlowPerTNLInformationList PRESENCE optional}|
{ ID id-ULForwardingUP-TNLInformation CRITICALITY reject EXTENSION UPTransportLayerInformation PRESENCE optional}|
{ ID id-AdditionalULForwardingUPTNLInformation CRITICALITY reject EXTENSION UPTransportLayerInformationList PRESENCE optional},
...
}
HandoverFlag ::= ENUMERATED {
handover-preparation,
...
}
HandoverPreparationUnsuccessfulTransfer ::= SEQUENCE {
cause Cause,
iE-Extensions ProtocolExtensionContainer { {HandoverPreparationUnsuccessfulTransfer-ExtIEs} } OPTIONAL,
...
}
HandoverPreparationUnsuccessfulTransfer-ExtIEs NGAP-PROTOCOL-EXTENSION ::= {
...
}
HandoverRequestAcknowledgeTransfer ::= SEQUENCE {
dL-NGU-UP-TNLInformation UPTransportLayerInformation,
dLForwardingUP-TNLInformation UPTransportLayerInformation OPTIONAL,
securityResult SecurityResult OPTIONAL,
qosFlowSetupResponseList QosFlowListWithDataForwarding,
qosFlowFailedToSetupList QosFlowListWithCause OPTIONAL,
dataForwardingResponseDRBList DataForwardingResponseDRBList OPTIONAL,
iE-Extensions ProtocolExtensionContainer { {HandoverRequestAcknowledgeTransfer-ExtIEs} } OPTIONAL,
...
}
HandoverRequestAcknowledgeTransfer-ExtIEs NGAP-PROTOCOL-EXTENSION ::= {
{ ID id-AdditionalDLUPTNLInformationForHOList CRITICALITY ignore EXTENSION AdditionalDLUPTNLInformationForHOList PRESENCE optional }|
{ ID id-ULForwardingUP-TNLInformation CRITICALITY reject EXTENSION UPTransportLayerInformation PRESENCE optional}|
{ ID id-AdditionalULForwardingUPTNLInformation CRITICALITY reject EXTENSION UPTransportLayerInformationList PRESENCE optional},
...
}
HandoverRequiredTransfer ::= SEQUENCE {
directForwardingPathAvailability DirectForwardingPathAvailability OPTIONAL,
iE-Extensions ProtocolExtensionContainer { {HandoverRequiredTransfer-ExtIEs} } OPTIONAL,
...
}
HandoverRequiredTransfer-ExtIEs NGAP-PROTOCOL-EXTENSION ::= {
...
}
HandoverResourceAllocationUnsuccessfulTransfer ::= SEQUENCE {
cause Cause,
criticalityDiagnostics CriticalityDiagnostics OPTIONAL,
iE-Extensions ProtocolExtensionContainer { {HandoverResourceAllocationUnsuccessfulTransfer-ExtIEs} } OPTIONAL,
...
}
HandoverResourceAllocationUnsuccessfulTransfer-ExtIEs NGAP-PROTOCOL-EXTENSION ::= {
...
}
HandoverType ::= ENUMERATED {
intra5gs,
fivegs-to-eps,
eps-to-5gs,
...
}
-- I
IMSVoiceSupportIndicator ::= ENUMERATED {
supported,
not-supported,
...
}
IndexToRFSP ::= INTEGER (1..256, ...)
InfoOnRecommendedCellsAndRANNodesForPaging ::= SEQUENCE {
recommendedCellsForPaging RecommendedCellsForPaging,
recommendRANNodesForPaging RecommendedRANNodesForPaging,
iE-Extensions ProtocolExtensionContainer { {InfoOnRecommendedCellsAndRANNodesForPaging-ExtIEs} } OPTIONAL,
...
}
InfoOnRecommendedCellsAndRANNodesForPaging-ExtIEs NGAP-PROTOCOL-EXTENSION ::= {
...
}
IntegrityProtectionIndication ::= ENUMERATED {
required,
preferred,
not-needed,
...
}
IntegrityProtectionResult ::= ENUMERATED {
performed,
not-performed,
...
}
IntendedNumberOfPagingAttempts ::= INTEGER (1..16, ...)
InterfacesToTrace ::= BIT STRING (SIZE(8))
-- J
-- K
-- L
LastVisitedCellInformation ::= CHOICE {
nGRANCell LastVisitedNGRANCellInformation,
eUTRANCell LastVisitedEUTRANCellInformation,
uTRANCell LastVisitedUTRANCellInformation,
gERANCell LastVisitedGERANCellInformation,
choice-Extensions ProtocolIE-SingleContainer { {LastVisitedCellInformation-ExtIEs} }
}
LastVisitedCellInformation-ExtIEs NGAP-PROTOCOL-IES ::= {
...
}
LastVisitedCellItem ::= SEQUENCE {
lastVisitedCellInformation LastVisitedCellInformation,
iE-Extensions ProtocolExtensionContainer { {LastVisitedCellItem-ExtIEs} } OPTIONAL,
...
}
LastVisitedCellItem-ExtIEs NGAP-PROTOCOL-EXTENSION ::= {
...
}
LastVisitedEUTRANCellInformation ::= OCTET STRING
LastVisitedGERANCellInformation ::= OCTET STRING
LastVisitedNGRANCellInformation::= SEQUENCE {
globalCellID NGRAN-CGI,
cellType CellType,
timeUEStayedInCell TimeUEStayedInCell,
timeUEStayedInCellEnhancedGranularity TimeUEStayedInCellEnhancedGranularity OPTIONAL,
hOCauseValue Cause OPTIONAL,
iE-Extensions ProtocolExtensionContainer { {LastVisitedNGRANCellInformation-ExtIEs} } OPTIONAL,
...
}
LastVisitedNGRANCellInformation-ExtIEs NGAP-PROTOCOL-EXTENSION ::= {
...
}
LastVisitedUTRANCellInformation ::= OCTET STRING
LocationReportingAdditionalInfo ::= ENUMERATED {
includePSCell,
...
}
LocationReportingReferenceID ::= INTEGER (1..64, ...)
LocationReportingRequestType ::= SEQUENCE {
eventType EventType,
reportArea ReportArea,
areaOfInterestList AreaOfInterestList OPTIONAL,
locationReportingReferenceIDToBeCancelled LocationReportingReferenceID OPTIONAL,
-- The above IE shall be present if the event type is set to “stop reporting UE presence in the area of interest”
iE-Extensions ProtocolExtensionContainer { {LocationReportingRequestType-ExtIEs} } OPTIONAL,
...
}
LocationReportingRequestType-ExtIEs NGAP-PROTOCOL-EXTENSION ::= {
{ ID id-LocationReportingAdditionalInfo CRITICALITY ignore EXTENSION LocationReportingAdditionalInfo PRESENCE optional },
...
}
-- M
MaskedIMEISV ::= BIT STRING (SIZE(64))
MaximumDataBurstVolume ::= INTEGER (0..4095, ...)
MessageIdentifier ::= BIT STRING (SIZE(16))
MaximumIntegrityProtectedDataRate ::= ENUMERATED {
bitrate64kbs,
maximum-UE-rate,
...
}
MICOModeIndication ::= ENUMERATED {
true,
...
}
MobilityRestrictionList ::= SEQUENCE {
servingPLMN PLMNIdentity,
equivalentPLMNs EquivalentPLMNs OPTIONAL,
rATRestrictions RATRestrictions OPTIONAL,
forbiddenAreaInformation ForbiddenAreaInformation OPTIONAL,
serviceAreaInformation ServiceAreaInformation OPTIONAL,
iE-Extensions ProtocolExtensionContainer { {MobilityRestrictionList-ExtIEs} } OPTIONAL,
...
}
MobilityRestrictionList-ExtIEs NGAP-PROTOCOL-EXTENSION ::= {
{ ID id-LastEUTRAN-PLMNIdentity CRITICALITY ignore EXTENSION PLMNIdentity PRESENCE optional }|
{ ID id-CNTypeRestrictionsForServing CRITICALITY ignore EXTENSION CNTypeRestrictionsForServing PRESENCE optional}|
{ ID id-CNTypeRestrictionsForEquivalent CRITICALITY ignore EXTENSION CNTypeRestrictionsForEquivalent PRESENCE optional},
...
}
-- N
N3IWF-ID ::= CHOICE {
n3IWF-ID BIT STRING (SIZE(16)),
choice-Extensions ProtocolIE-SingleContainer { {N3IWF-ID-ExtIEs} }
}
N3IWF-ID-ExtIEs NGAP-PROTOCOL-IES ::= {
...
}
NAS-PDU ::= OCTET STRING
NASSecurityParametersFromNGRAN ::= OCTET STRING
NetworkInstance ::= INTEGER (1..256, ...)
NewSecurityContextInd ::= ENUMERATED {
true,
...
}
NextHopChainingCount ::= INTEGER (0..7)
NextPagingAreaScope ::= ENUMERATED {
same,
changed,
...
}
NgENB-ID ::= CHOICE {
macroNgENB-ID BIT STRING (SIZE(20)),
shortMacroNgENB-ID BIT STRING (SIZE(18)),
longMacroNgENB-ID BIT STRING (SIZE(21)),
choice-Extensions ProtocolIE-SingleContainer { {NgENB-ID-ExtIEs} }
}
NgENB-ID-ExtIEs NGAP-PROTOCOL-IES ::= {
...
}
NGRAN-CGI ::= CHOICE {
nR-CGI NR-CGI,
eUTRA-CGI EUTRA-CGI,
choice-Extensions ProtocolIE-SingleContainer { {NGRAN-CGI-ExtIEs} }
}
NGRAN-CGI-ExtIEs NGAP-PROTOCOL-IES ::= {
...
}
NGRAN-TNLAssociationToRemoveList ::= SEQUENCE (SIZE(1..maxnoofTNLAssociations)) OF NGRAN-TNLAssociationToRemoveItem
NGRAN-TNLAssociationToRemoveItem::= SEQUENCE {
tNLAssociationTransportLayerAddress CPTransportLayerInformation,
tNLAssociationTransportLayerAddressAMF CPTransportLayerInformation OPTIONAL,
iE-Extensions ProtocolExtensionContainer { { NGRAN-TNLAssociationToRemoveItem-ExtIEs} } OPTIONAL
}
NGRAN-TNLAssociationToRemoveItem-ExtIEs NGAP-PROTOCOL-EXTENSION ::= {
...
}
NGRANTraceID ::= OCTET STRING (SIZE(8))
NonDynamic5QIDescriptor ::= SEQUENCE {
fiveQI FiveQI,
priorityLevelQos PriorityLevelQos OPTIONAL,
averagingWindow AveragingWindow OPTIONAL,
maximumDataBurstVolume MaximumDataBurstVolume OPTIONAL,
iE-Extensions ProtocolExtensionContainer { {NonDynamic5QIDescriptor-ExtIEs} } OPTIONAL,
...
}
NonDynamic5QIDescriptor-ExtIEs NGAP-PROTOCOL-EXTENSION ::= {
...
}
NotAllowedTACs ::= SEQUENCE (SIZE(1..maxnoofAllowedAreas)) OF TAC
NotificationCause ::= ENUMERATED {
fulfilled,
not-fulfilled,
...
}
NotificationControl ::= ENUMERATED {
notification-requested,
...
}
NRCellIdentity ::= BIT STRING (SIZE(36))
NR-CGI ::= SEQUENCE {
pLMNIdentity PLMNIdentity,
nRCellIdentity NRCellIdentity,
iE-Extensions ProtocolExtensionContainer { {NR-CGI-ExtIEs} } OPTIONAL,
...
}
NR-CGI-ExtIEs NGAP-PROTOCOL-EXTENSION ::= {
...
}
NR-CGIList ::= SEQUENCE (SIZE(1..maxnoofCellsingNB)) OF NR-CGI
NR-CGIListForWarning ::= SEQUENCE (SIZE(1..maxnoofCellIDforWarning)) OF NR-CGI
NRencryptionAlgorithms ::= BIT STRING (SIZE(16, ...))
NRintegrityProtectionAlgorithms ::= BIT STRING (SIZE(16, ...))
NRPPa-PDU ::= OCTET STRING
NumberOfBroadcasts ::= INTEGER (0..65535)
NumberOfBroadcastsRequested ::= INTEGER (0..65535)
-- O
OverloadAction ::= ENUMERATED {
reject-non-emergency-mo-dt,
reject-rrc-cr-signalling,
permit-emergency-sessions-and-mobile-terminated-services-only,
permit-high-priority-sessions-and-mobile-terminated-services-only,
...
}
OverloadResponse ::= CHOICE {
overloadAction OverloadAction,
choice-Extensions ProtocolIE-SingleContainer { {OverloadResponse-ExtIEs} }
}
OverloadResponse-ExtIEs NGAP-PROTOCOL-IES ::= {
...
}
OverloadStartNSSAIList ::= SEQUENCE (SIZE (1..maxnoofSliceItems)) OF OverloadStartNSSAIItem
OverloadStartNSSAIItem ::= SEQUENCE {
sliceOverloadList SliceOverloadList,
sliceOverloadResponse OverloadResponse OPTIONAL,
sliceTrafficLoadReductionIndication TrafficLoadReductionIndication OPTIONAL,
iE-Extensions ProtocolExtensionContainer { {OverloadStartNSSAIItem-ExtIEs} } OPTIONAL,
...
}
OverloadStartNSSAIItem-ExtIEs NGAP-PROTOCOL-EXTENSION ::= {
...
}
-- P
PacketDelayBudget ::= INTEGER (0..1023, ...)
PacketErrorRate ::= SEQUENCE {
pERScalar INTEGER (0..9, ...),
pERExponent INTEGER (0..9, ...),
iE-Extensions ProtocolExtensionContainer { {PacketErrorRate-ExtIEs} } OPTIONAL,
...
}
PacketErrorRate-ExtIEs NGAP-PROTOCOL-EXTENSION ::= {
...
}
PacketLossRate ::= INTEGER (0..1000, ...)
PagingAttemptInformation ::= SEQUENCE {
pagingAttemptCount PagingAttemptCount,
intendedNumberOfPagingAttempts IntendedNumberOfPagingAttempts,
nextPagingAreaScope NextPagingAreaScope OPTIONAL,
iE-Extensions ProtocolExtensionContainer { {PagingAttemptInformation-ExtIEs} } OPTIONAL,
...
}
PagingAttemptInformation-ExtIEs NGAP-PROTOCOL-EXTENSION ::= {
...
}
PagingAttemptCount ::= INTEGER (1..16, ...)
PagingDRX ::= ENUMERATED {
v32,
v64,
v128,
v256,
...
}
PagingOrigin ::= ENUMERATED {
non-3gpp,
...
}
PagingPriority ::= ENUMERATED {
priolevel1,
priolevel2,
priolevel3,
priolevel4,
priolevel5,
priolevel6,
priolevel7,
priolevel8,
...
}
PathSwitchRequestAcknowledgeTransfer ::= SEQUENCE {
uL-NGU-UP-TNLInformation UPTransportLayerInformation OPTIONAL,
securityIndication SecurityIndication OPTIONAL,
iE-Extensions ProtocolExtensionContainer { {PathSwitchRequestAcknowledgeTransfer-ExtIEs} } OPTIONAL,
...
}
PathSwitchRequestAcknowledgeTransfer-ExtIEs NGAP-PROTOCOL-EXTENSION ::= {
{ ID id-AdditionalNGU-UP-TNLInformation CRITICALITY ignore EXTENSION UPTransportLayerInformationPairList PRESENCE optional },
...
}
PathSwitchRequestSetupFailedTransfer ::= SEQUENCE {
cause Cause,
iE-Extensions ProtocolExtensionContainer { {PathSwitchRequestSetupFailedTransfer-ExtIEs} } OPTIONAL,
...
}
PathSwitchRequestSetupFailedTransfer-ExtIEs NGAP-PROTOCOL-EXTENSION ::= {
...
}
PathSwitchRequestTransfer ::= SEQUENCE {
dL-NGU-UP-TNLInformation UPTransportLayerInformation,
dL-NGU-TNLInformationReused DL-NGU-TNLInformationReused OPTIONAL,
userPlaneSecurityInformation UserPlaneSecurityInformation OPTIONAL,
qosFlowAcceptedList QosFlowAcceptedList,
iE-Extensions ProtocolExtensionContainer { {PathSwitchRequestTransfer-ExtIEs} } OPTIONAL,
...
}
PathSwitchRequestTransfer-ExtIEs NGAP-PROTOCOL-EXTENSION ::= {
{ ID id-AdditionalDLQosFlowPerTNLInformation CRITICALITY ignore EXTENSION QosFlowPerTNLInformationList PRESENCE optional },
...
}
PathSwitchRequestUnsuccessfulTransfer ::= SEQUENCE {
cause Cause,
iE-Extensions ProtocolExtensionContainer { {PathSwitchRequestUnsuccessfulTransfer-ExtIEs} } OPTIONAL,
...
}
PathSwitchRequestUnsuccessfulTransfer-ExtIEs NGAP-PROTOCOL-EXTENSION ::= {
...
}
PDUSessionAggregateMaximumBitRate ::= SEQUENCE {
pDUSessionAggregateMaximumBitRateDL BitRate,
pDUSessionAggregateMaximumBitRateUL BitRate,
iE-Extensions ProtocolExtensionContainer { {PDUSessionAggregateMaximumBitRate-ExtIEs} } OPTIONAL,
...
}
PDUSessionAggregateMaximumBitRate-ExtIEs NGAP-PROTOCOL-EXTENSION ::= {
...
}
PDUSessionID ::= INTEGER (0..255)
PDUSessionResourceAdmittedList ::= SEQUENCE (SIZE(1..maxnoofPDUSessions)) OF PDUSessionResourceAdmittedItem
PDUSessionResourceAdmittedItem ::= SEQUENCE {
pDUSessionID PDUSessionID,
handoverRequestAcknowledgeTransfer OCTET STRING (CONTAINING HandoverRequestAcknowledgeTransfer),
iE-Extensions ProtocolExtensionContainer { {PDUSessionResourceAdmittedItem-ExtIEs} } OPTIONAL,
...
}
PDUSessionResourceAdmittedItem-ExtIEs NGAP-PROTOCOL-EXTENSION ::= {
...
}
PDUSessionResourceFailedToModifyListModCfm ::= SEQUENCE (SIZE(1..maxnoofPDUSessions)) OF PDUSessionResourceFailedToModifyItemModCfm
PDUSessionResourceFailedToModifyItemModCfm ::= SEQUENCE {
pDUSessionID PDUSessionID,
pDUSessionResourceModifyIndicationUnsuccessfulTransfer OCTET STRING (CONTAINING PDUSessionResourceModifyIndicationUnsuccessfulTransfer),
iE-Extensions ProtocolExtensionContainer { {PDUSessionResourceFailedToModifyItemModCfm-ExtIEs} } OPTIONAL,
...
}
PDUSessionResourceFailedToModifyItemModCfm-ExtIEs NGAP-PROTOCOL-EXTENSION ::= {
...
}
PDUSessionResourceFailedToModifyListModRes ::= SEQUENCE (SIZE(1..maxnoofPDUSessions)) OF PDUSessionResourceFailedToModifyItemModRes
PDUSessionResourceFailedToModifyItemModRes ::= SEQUENCE {
pDUSessionID PDUSessionID,
pDUSessionResourceModifyUnsuccessfulTransfer OCTET STRING (CONTAINING PDUSessionResourceModifyUnsuccessfulTransfer),
iE-Extensions ProtocolExtensionContainer { {PDUSessionResourceFailedToModifyItemModRes-ExtIEs} } OPTIONAL,
...
}
PDUSessionResourceFailedToModifyItemModRes-ExtIEs NGAP-PROTOCOL-EXTENSION ::= {
...
}
PDUSessionResourceFailedToSetupListCxtFail ::= SEQUENCE (SIZE(1..maxnoofPDUSessions)) OF PDUSessionResourceFailedToSetupItemCxtFail
PDUSessionResourceFailedToSetupItemCxtFail ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemCxtFail-ExtIEs} } OPTIONAL,
...
}
PDUSessionResourceFailedToSetupItemCxtFail-ExtIEs NGAP-PROTOCOL-EXTENSION ::= {
...
}
PDUSessionResourceFailedToSetupListCxtRes ::= SEQUENCE (SIZE(1..maxnoofPDUSessions)) OF PDUSessionResourceFailedToSetupItemCxtRes
PDUSessionResourceFailedToSetupItemCxtRes ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemCxtRes-ExtIEs} } OPTIONAL,
...
}
PDUSessionResourceFailedToSetupItemCxtRes-ExtIEs NGAP-PROTOCOL-EXTENSION ::= {
...
}
PDUSessionResourceFailedToSetupListHOAck ::= SEQUENCE (SIZE(1..maxnoofPDUSessions)) OF PDUSessionResourceFailedToSetupItemHOAck
PDUSessionResourceFailedToSetupItemHOAck ::= SEQUENCE {
pDUSessionID PDUSessionID,
handoverResourceAllocationUnsuccessfulTransfer OCTET STRING (CONTAINING HandoverResourceAllocationUnsuccessfulTransfer),
iE-Extensions ProtocolExtensionContainer { {PDUSessionResourceFailedToSetupItemHOAck-ExtIEs} } OPTIONAL,
...
}
PDUSessionResourceFailedToSetupItemHOAck-ExtIEs NGAP-PROTOCOL-EXTENSION ::= {
...
}
PDUSessionResourceFailedToSetupListPSReq ::= SEQUENCE (SIZE(1..maxnoofPDUSessions)) OF PDUSessionResourceFailedToSetupItemPSReq
PDUSessionResourceFailedToSetupItemPSReq ::= SEQUENCE {
pDUSessionID PDUSessionID,
pathSwitchRequestSetupFailedTransfer OCTET STRING (CONTAINING PathSwitchRequestSetupFailedTransfer),
iE-Extensions ProtocolExtensionContainer { {PDUSessionResourceFailedToSetupItemPSReq-ExtIEs} } OPTIONAL,
...
}
PDUSessionResourceFailedToSetupItemPSReq-ExtIEs NGAP-PROTOCOL-EXTENSION ::= {
...
}
PDUSessionResourceFailedToSetupListSURes ::= SEQUENCE (SIZE(1..maxnoofPDUSessions)) OF PDUSessionResourceFailedToSetupItemSURes
PDUSessionResourceFailedToSetupItemSURes ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemSURes-ExtIEs} } OPTIONAL,
...
}
PDUSessionResourceFailedToSetupItemSURes-ExtIEs NGAP-PROTOCOL-EXTENSION ::= {
...
}
PDUSessionResourceHandoverList ::= SEQUENCE (SIZE(1..maxnoofPDUSessions)) OF PDUSessionResourceHandoverItem
PDUSessionResourceHandoverItem ::= SEQUENCE {
pDUSessionID PDUSessionID,
handoverCommandTransfer OCTET STRING (CONTAINING HandoverCommandTransfer),
iE-Extensions ProtocolExtensionContainer { {PDUSessionResourceHandoverItem-ExtIEs} } OPTIONAL,
...
}
PDUSessionResourceHandoverItem-ExtIEs NGAP-PROTOCOL-EXTENSION ::= {
...
}
PDUSessionResourceInformationList ::= SEQUENCE (SIZE(1..maxnoofPDUSessions)) OF PDUSessionResourceInformationItem
PDUSessionResourceInformationItem ::= SEQUENCE {
pDUSessionID PDUSessionID,
qosFlowInformationList QosFlowInformationList,
dRBsToQosFlowsMappingList DRBsToQosFlowsMappingList OPTIONAL,
iE-Extensions ProtocolExtensionContainer { {PDUSessionResourceInformationItem-ExtIEs} } OPTIONAL,
...
}
PDUSessionResourceInformationItem-ExtIEs NGAP-PROTOCOL-EXTENSION ::= {
...
}
PDUSessionResourceListCxtRelCpl ::= SEQUENCE (SIZE(1..maxnoofPDUSessions)) OF PDUSessionResourceItemCxtRelCpl
PDUSessionResourceItemCxtRelCpl ::= SEQUENCE {
pDUSessionID PDUSessionID,
iE-Extensions ProtocolExtensionContainer { {PDUSessionResourceItemCxtRelCpl-ExtIEs} } OPTIONAL,
...
}
PDUSessionResourceItemCxtRelCpl-ExtIEs NGAP-PROTOCOL-EXTENSION ::= {
{ ID id-PDUSessionResourceReleaseResponseTransfer CRITICALITY ignore EXTENSION OCTET STRING (CONTAINING PDUSessionResourceReleaseResponseTransfer) PRESENCE optional },
...
}
PDUSessionResourceListCxtRelReq ::= SEQUENCE (SIZE(1..maxnoofPDUSessions)) OF PDUSessionResourceItemCxtRelReq
PDUSessionResourceItemCxtRelReq ::= SEQUENCE {
pDUSessionID PDUSessionID,
iE-Extensions ProtocolExtensionContainer { {PDUSessionResourceItemCxtRelReq-ExtIEs} } OPTIONAL,
...
}
PDUSessionResourceItemCxtRelReq-ExtIEs NGAP-PROTOCOL-EXTENSION ::= {
...
}
PDUSessionResourceListHORqd ::= SEQUENCE (SIZE(1..maxnoofPDUSessions)) OF PDUSessionResourceItemHORqd
PDUSessionResourceItemHORqd ::= SEQUENCE {
pDUSessionID PDUSessionID,
handoverRequiredTransfer OCTET STRING (CONTAINING HandoverRequiredTransfer),
iE-Extensions ProtocolExtensionContainer { {PDUSessionResourceItemHORqd-ExtIEs} } OPTIONAL,
...
}
PDUSessionResourceItemHORqd-ExtIEs NGAP-PROTOCOL-EXTENSION ::= {
...
}
PDUSessionResourceModifyConfirmTransfer ::= SEQUENCE {
qosFlowModifyConfirmList QosFlowModifyConfirmList,
uLNGU-UP-TNLInformation UPTransportLayerInformation,
additionalNG-UUPTNLInformation UPTransportLayerInformationPairList OPTIONAL,
qosFlowFailedToModifyList QosFlowListWithCause OPTIONAL,
iE-Extensions ProtocolExtensionContainer { {PDUSessionResourceModifyConfirmTransfer-ExtIEs} } OPTIONAL,
...
}
PDUSessionResourceModifyConfirmTransfer-ExtIEs NGAP-PROTOCOL-EXTENSION ::= {
...
}
PDUSessionResourceModifyIndicationUnsuccessfulTransfer ::= SEQUENCE {
cause Cause,
iE-Extensions ProtocolExtensionContainer { {PDUSessionResourceModifyIndicationUnsuccessfulTransfer-ExtIEs} } OPTIONAL,
...
}
PDUSessionResourceModifyIndicationUnsuccessfulTransfer-ExtIEs NGAP-PROTOCOL-EXTENSION ::= {
...
}
PDUSessionResourceModifyRequestTransfer ::= SEQUENCE {
protocolIEs ProtocolIE-Container { {PDUSessionResourceModifyRequestTransferIEs} },
...
}
PDUSessionResourceModifyRequestTransferIEs NGAP-PROTOCOL-IES ::= {
{ ID id-PDUSessionAggregateMaximumBitRate CRITICALITY reject TYPE PDUSessionAggregateMaximumBitRate PRESENCE optional }|
{ ID id-UL-NGU-UP-TNLModifyList CRITICALITY reject TYPE UL-NGU-UP-TNLModifyList PRESENCE optional }|
{ ID id-NetworkInstance CRITICALITY reject TYPE NetworkInstance PRESENCE optional }|
{ ID id-QosFlowAddOrModifyRequestList CRITICALITY reject TYPE QosFlowAddOrModifyRequestList PRESENCE optional }|
{ ID id-QosFlowToReleaseList CRITICALITY reject TYPE QosFlowListWithCause PRESENCE optional }|
{ ID id-AdditionalUL-NGU-UP-TNLInformation CRITICALITY reject TYPE UPTransportLayerInformationList PRESENCE optional }|
{ ID id-CommonNetworkInstance CRITICALITY ignore TYPE CommonNetworkInstance PRESENCE optional },
...
}
PDUSessionResourceModifyResponseTransfer ::= SEQUENCE {
dL-NGU-UP-TNLInformation UPTransportLayerInformation OPTIONAL,
uL-NGU-UP-TNLInformation UPTransportLayerInformation OPTIONAL,
qosFlowAddOrModifyResponseList QosFlowAddOrModifyResponseList OPTIONAL,
additionalDLQosFlowPerTNLInformation QosFlowPerTNLInformationList OPTIONAL,
qosFlowFailedToAddOrModifyList QosFlowListWithCause OPTIONAL,
iE-Extensions ProtocolExtensionContainer { {PDUSessionResourceModifyResponseTransfer-ExtIEs} } OPTIONAL,
...
}
PDUSessionResourceModifyResponseTransfer-ExtIEs NGAP-PROTOCOL-EXTENSION ::= {
{ ID id-AdditionalNGU-UP-TNLInformation CRITICALITY ignore EXTENSION UPTransportLayerInformationPairList PRESENCE optional },
...
}
PDUSessionResourceModifyIndicationTransfer ::= SEQUENCE {
dLQosFlowPerTNLInformation QosFlowPerTNLInformation,
additionalDLQosFlowPerTNLInformation QosFlowPerTNLInformationList OPTIONAL,
iE-Extensions ProtocolExtensionContainer { {PDUSessionResourceModifyIndicationTransfer-ExtIEs} } OPTIONAL,
...
}
PDUSessionResourceModifyIndicationTransfer-ExtIEs NGAP-PROTOCOL-EXTENSION ::= {
{ ID id-SecondaryRATUsageInformation CRITICALITY ignore EXTENSION SecondaryRATUsageInformation PRESENCE optional }|
{ ID id-SecurityResult CRITICALITY ignore EXTENSION SecurityResult PRESENCE optional },
...
}
PDUSessionResourceModifyListModCfm ::= SEQUENCE (SIZE(1..maxnoofPDUSessions)) OF PDUSessionResourceModifyItemModCfm
PDUSessionResourceModifyItemModCfm ::= SEQUENCE {
pDUSessionID PDUSessionID,
pDUSessionResourceModifyConfirmTransfer OCTET STRING (CONTAINING PDUSessionResourceModifyConfirmTransfer),
iE-Extensions ProtocolExtensionContainer { {PDUSessionResourceModifyItemModCfm-ExtIEs} } OPTIONAL,
...
}
PDUSessionResourceModifyItemModCfm-ExtIEs NGAP-PROTOCOL-EXTENSION ::= {
...
}
PDUSessionResourceModifyListModInd ::= SEQUENCE (SIZE(1..maxnoofPDUSessions)) OF PDUSessionResourceModifyItemModInd
PDUSessionResourceModifyItemModInd ::= SEQUENCE {
pDUSessionID PDUSessionID,
pDUSessionResourceModifyIndicationTransfer OCTET STRING (CONTAINING PDUSessionResourceModifyIndicationTransfer),
iE-Extensions ProtocolExtensionContainer { {PDUSessionResourceModifyItemModInd-ExtIEs} } OPTIONAL,
...
}
PDUSessionResourceModifyItemModInd-ExtIEs NGAP-PROTOCOL-EXTENSION ::= {
...
}
PDUSessionResourceModifyListModReq ::= SEQUENCE (SIZE(1..maxnoofPDUSessions)) OF PDUSessionResourceModifyItemModReq
PDUSessionResourceModifyItemModReq ::= SEQUENCE {
pDUSessionID PDUSessionID,
nAS-PDU NAS-PDU OPTIONAL,
pDUSessionResourceModifyRequestTransfer OCTET STRING (CONTAINING PDUSessionResourceModifyRequestTransfer),
iE-Extensions ProtocolExtensionContainer { {PDUSessionResourceModifyItemModReq-ExtIEs} } OPTIONAL,
...
}
PDUSessionResourceModifyItemModReq-ExtIEs NGAP-PROTOCOL-EXTENSION ::= {
{ID id-S-NSSAI CRITICALITY reject EXTENSION S-NSSAI PRESENCE optional },
...
}
PDUSessionResourceModifyListModRes ::= SEQUENCE (SIZE(1..maxnoofPDUSessions)) OF PDUSessionResourceModifyItemModRes
PDUSessionResourceModifyItemModRes ::= SEQUENCE {
pDUSessionID PDUSessionID,
pDUSessionResourceModifyResponseTransfer OCTET STRING (CONTAINING PDUSessionResourceModifyResponseTransfer),
iE-Extensions ProtocolExtensionContainer { {PDUSessionResourceModifyItemModRes-ExtIEs} } OPTIONAL,
...
}
PDUSessionResourceModifyItemModRes-ExtIEs NGAP-PROTOCOL-EXTENSION ::= {
...
}
PDUSessionResourceModifyUnsuccessfulTransfer ::= SEQUENCE {
cause Cause,
criticalityDiagnostics CriticalityDiagnostics OPTIONAL,
iE-Extensions ProtocolExtensionContainer { {PDUSessionResourceModifyUnsuccessfulTransfer-ExtIEs} } OPTIONAL,
...
}
PDUSessionResourceModifyUnsuccessfulTransfer-ExtIEs NGAP-PROTOCOL-EXTENSION ::= {
...
}
PDUSessionResourceNotifyList ::= SEQUENCE (SIZE(1..maxnoofPDUSessions)) OF PDUSessionResourceNotifyItem
PDUSessionResourceNotifyItem ::= SEQUENCE {
pDUSessionID PDUSessionID,
pDUSessionResourceNotifyTransfer OCTET STRING (CONTAINING PDUSessionResourceNotifyTransfer),
iE-Extensions ProtocolExtensionContainer { {PDUSessionResourceNotifyItem-ExtIEs} } OPTIONAL,
...
}
PDUSessionResourceNotifyItem-ExtIEs NGAP-PROTOCOL-EXTENSION ::= {
...
}
PDUSessionResourceNotifyReleasedTransfer ::= SEQUENCE {
cause Cause,
iE-Extensions ProtocolExtensionContainer { {PDUSessionResourceNotifyReleasedTransfer-ExtIEs} } OPTIONAL,
...
}
PDUSessionResourceNotifyReleasedTransfer-ExtIEs NGAP-PROTOCOL-EXTENSION ::= {
{ ID id-SecondaryRATUsageInformation CRITICALITY ignore EXTENSION SecondaryRATUsageInformation PRESENCE optional },
...
}
PDUSessionResourceNotifyTransfer ::= SEQUENCE {
qosFlowNotifyList QosFlowNotifyList OPTIONAL,
qosFlowReleasedList QosFlowListWithCause OPTIONAL,
iE-Extensions ProtocolExtensionContainer { {PDUSessionResourceNotifyTransfer-ExtIEs} } OPTIONAL,
...
}
PDUSessionResourceNotifyTransfer-ExtIEs NGAP-PROTOCOL-EXTENSION ::= {
{ ID id-SecondaryRATUsageInformation CRITICALITY ignore EXTENSION SecondaryRATUsageInformation PRESENCE optional },
...
}
PDUSessionResourceReleaseCommandTransfer ::= SEQUENCE {
cause Cause,
iE-Extensions ProtocolExtensionContainer { {PDUSessionResourceReleaseCommandTransfer-ExtIEs} } OPTIONAL,
...
}
PDUSessionResourceReleaseCommandTransfer-ExtIEs NGAP-PROTOCOL-EXTENSION ::= {
...
}
PDUSessionResourceReleasedListNot ::= SEQUENCE (SIZE(1..maxnoofPDUSessions)) OF PDUSessionResourceReleasedItemNot
PDUSessionResourceReleasedItemNot ::= SEQUENCE {
pDUSessionID PDUSessionID,
pDUSessionResourceNotifyReleasedTransfer OCTET STRING (CONTAINING PDUSessionResourceNotifyReleasedTransfer),
iE-Extensions ProtocolExtensionContainer { {PDUSessionResourceReleasedItemNot-ExtIEs} } OPTIONAL,
...
}
PDUSessionResourceReleasedItemNot-ExtIEs NGAP-PROTOCOL-EXTENSION ::= {
...
}
PDUSessionResourceReleasedListPSAck ::= SEQUENCE (SIZE(1..maxnoofPDUSessions)) OF PDUSessionResourceReleasedItemPSAck
PDUSessionResourceReleasedItemPSAck ::= SEQUENCE {
pDUSessionID PDUSessionID,
pathSwitchRequestUnsuccessfulTransfer OCTET STRING (CONTAINING PathSwitchRequestUnsuccessfulTransfer),
iE-Extensions ProtocolExtensionContainer { {PDUSessionResourceReleasedItemPSAck-ExtIEs} } OPTIONAL,
...
}
PDUSessionResourceReleasedItemPSAck-ExtIEs NGAP-PROTOCOL-EXTENSION ::= {
...
}
PDUSessionResourceReleasedListPSFail ::= SEQUENCE (SIZE(1..maxnoofPDUSessions)) OF PDUSessionResourceReleasedItemPSFail
PDUSessionResourceReleasedItemPSFail ::= SEQUENCE {
pDUSessionID PDUSessionID,
pathSwitchRequestUnsuccessfulTransfer OCTET STRING (CONTAINING PathSwitchRequestUnsuccessfulTransfer),
iE-Extensions ProtocolExtensionContainer { {PDUSessionResourceReleasedItemPSFail-ExtIEs} } OPTIONAL,
...
}
PDUSessionResourceReleasedItemPSFail-ExtIEs NGAP-PROTOCOL-EXTENSION ::= {
...
}
PDUSessionResourceReleasedListRelRes ::= SEQUENCE (SIZE(1..maxnoofPDUSessions)) OF PDUSessionResourceReleasedItemRelRes
PDUSessionResourceReleasedItemRelRes ::= SEQUENCE {
pDUSessionID PDUSessionID,
pDUSessionResourceReleaseResponseTransfer OCTET STRING (CONTAINING PDUSessionResourceReleaseResponseTransfer),
iE-Extensions ProtocolExtensionContainer { {PDUSessionResourceReleasedItemRelRes-ExtIEs} } OPTIONAL,
...
}
PDUSessionResourceReleasedItemRelRes-ExtIEs NGAP-PROTOCOL-EXTENSION ::= {
...
}
PDUSessionResourceReleaseResponseTransfer ::= SEQUENCE {
iE-Extensions ProtocolExtensionContainer { {PDUSessionResourceReleaseResponseTransfer-ExtIEs} } OPTIONAL,
...
}
PDUSessionResourceReleaseResponseTransfer-ExtIEs NGAP-PROTOCOL-EXTENSION ::= {
{ ID id-SecondaryRATUsageInformation CRITICALITY ignore EXTENSION SecondaryRATUsageInformation PRESENCE optional },
...
}
PDUSessionResourceSecondaryRATUsageList ::= SEQUENCE (SIZE(1..maxnoofPDUSessions)) OF PDUSessionResourceSecondaryRATUsageItem
PDUSessionResourceSecondaryRATUsageItem ::= SEQUENCE {
pDUSessionID PDUSessionID,
secondaryRATDataUsageReportTransfer OCTET STRING (CONTAINING SecondaryRATDataUsageReportTransfer),
iE-Extensions ProtocolExtensionContainer { {PDUSessionResourceSecondaryRATUsageItem-ExtIEs} } OPTIONAL,
...
}
PDUSessionResourceSecondaryRATUsageItem-ExtIEs NGAP-PROTOCOL-EXTENSION ::= {
...
}
PDUSessionResourceSetupListCxtReq ::= SEQUENCE (SIZE(1..maxnoofPDUSessions)) OF PDUSessionResourceSetupItemCxtReq
PDUSessionResourceSetupItemCxtReq ::= SEQUENCE {
pDUSessionID PDUSessionID,
nAS-PDU NAS-PDU OPTIONAL,
s-NSSAI S-NSSAI,
pDUSessionResourceSetupRequestTransfer OCTET STRING (CONTAINING PDUSessionResourceSetupRequestTransfer),
iE-Extensions ProtocolExtensionContainer { {PDUSessionResourceSetupItemCxtReq-ExtIEs} } OPTIONAL,
...
}
PDUSessionResourceSetupItemCxtReq-ExtIEs NGAP-PROTOCOL-EXTENSION ::= {
...
}
PDUSessionResourceSetupListCxtRes ::= SEQUENCE (SIZE(1..maxnoofPDUSessions)) OF PDUSessionResourceSetupItemCxtRes
PDUSessionResourceSetupItemCxtRes ::= SEQUENCE {
pDUSessionID PDUSessionID,
pDUSessionResourceSetupResponseTransfer OCTET STRING (CONTAINING PDUSessionResourceSetupResponseTransfer),
iE-Extensions ProtocolExtensionContainer { {PDUSessionResourceSetupItemCxtRes-ExtIEs} } OPTIONAL,
...
}
PDUSessionResourceSetupItemCxtRes-ExtIEs NGAP-PROTOCOL-EXTENSION ::= {
...
}
PDUSessionResourceSetupListHOReq ::= SEQUENCE (SIZE(1..maxnoofPDUSessions)) OF PDUSessionResourceSetupItemHOReq
PDUSessionResourceSetupItemHOReq ::= SEQUENCE {
pDUSessionID PDUSessionID,
s-NSSAI S-NSSAI,
handoverRequestTransfer OCTET STRING (CONTAINING PDUSessionResourceSetupRequestTransfer),
iE-Extensions ProtocolExtensionContainer { {PDUSessionResourceSetupItemHOReq-ExtIEs} } OPTIONAL,
...
}
PDUSessionResourceSetupItemHOReq-ExtIEs NGAP-PROTOCOL-EXTENSION ::= {
...
}
PDUSessionResourceSetupListSUReq ::= SEQUENCE (SIZE(1..maxnoofPDUSessions)) OF PDUSessionResourceSetupItemSUReq
PDUSessionResourceSetupItemSUReq ::= SEQUENCE {
pDUSessionID PDUSessionID,
pDUSessionNAS-PDU NAS-PDU OPTIONAL,
s-NSSAI S-NSSAI,
pDUSessionResourceSetupRequestTransfer OCTET STRING (CONTAINING PDUSessionResourceSetupRequestTransfer),
iE-Extensions ProtocolExtensionContainer { {PDUSessionResourceSetupItemSUReq-ExtIEs} } OPTIONAL,
...
}
PDUSessionResourceSetupItemSUReq-ExtIEs NGAP-PROTOCOL-EXTENSION ::= {
...
}
PDUSessionResourceSetupListSURes ::= SEQUENCE (SIZE(1..maxnoofPDUSessions)) OF PDUSessionResourceSetupItemSURes
PDUSessionResourceSetupItemSURes ::= SEQUENCE {
pDUSessionID PDUSessionID,
pDUSessionResourceSetupResponseTransfer OCTET STRING (CONTAINING PDUSessionResourceSetupResponseTransfer),
iE-Extensions ProtocolExtensionContainer { {PDUSessionResourceSetupItemSURes-ExtIEs} } OPTIONAL,
...
}
PDUSessionResourceSetupItemSURes-ExtIEs NGAP-PROTOCOL-EXTENSION ::= {
...
}
PDUSessionResourceSetupRequestTransfer ::= SEQUENCE {
protocolIEs ProtocolIE-Container { {PDUSessionResourceSetupRequestTransferIEs} },
...
}
PDUSessionResourceSetupRequestTransferIEs NGAP-PROTOCOL-IES ::= {
{ ID id-PDUSessionAggregateMaximumBitRate CRITICALITY reject TYPE PDUSessionAggregateMaximumBitRate PRESENCE optional }|
{ ID id-UL-NGU-UP-TNLInformation CRITICALITY reject TYPE UPTransportLayerInformation PRESENCE mandatory }|
{ ID id-AdditionalUL-NGU-UP-TNLInformation CRITICALITY reject TYPE UPTransportLayerInformationList PRESENCE optional }|
{ ID id-DataForwardingNotPossible CRITICALITY reject TYPE DataForwardingNotPossible PRESENCE optional }|
{ ID id-PDUSessionType CRITICALITY reject TYPE PDUSessionType PRESENCE mandatory }|
{ ID id-SecurityIndication CRITICALITY reject TYPE SecurityIndication PRESENCE optional }|
{ ID id-NetworkInstance CRITICALITY reject TYPE NetworkInstance PRESENCE optional }|
{ ID id-QosFlowSetupRequestList CRITICALITY reject TYPE QosFlowSetupRequestList PRESENCE mandatory }|
{ ID id-CommonNetworkInstance CRITICALITY ignore TYPE CommonNetworkInstance PRESENCE optional },
...
}
PDUSessionResourceSetupResponseTransfer ::= SEQUENCE {
dLQosFlowPerTNLInformation QosFlowPerTNLInformation,
additionalDLQosFlowPerTNLInformation QosFlowPerTNLInformationList OPTIONAL,
securityResult SecurityResult OPTIONAL,
qosFlowFailedToSetupList QosFlowListWithCause OPTIONAL,
iE-Extensions ProtocolExtensionContainer { {PDUSessionResourceSetupResponseTransfer-ExtIEs} } OPTIONAL,
...
}
PDUSessionResourceSetupResponseTransfer-ExtIEs NGAP-PROTOCOL-EXTENSION ::= {
...
}
PDUSessionResourceSetupUnsuccessfulTransfer ::= SEQUENCE {
cause Cause,
criticalityDiagnostics CriticalityDiagnostics OPTIONAL,
iE-Extensions ProtocolExtensionContainer { {PDUSessionResourceSetupUnsuccessfulTransfer-ExtIEs} } OPTIONAL,
...
}
PDUSessionResourceSetupUnsuccessfulTransfer-ExtIEs NGAP-PROTOCOL-EXTENSION ::= {
...
}
PDUSessionResourceSwitchedList ::= SEQUENCE (SIZE(1..maxnoofPDUSessions)) OF PDUSessionResourceSwitchedItem
PDUSessionResourceSwitchedItem ::= SEQUENCE {
pDUSessionID PDUSessionID,
pathSwitchRequestAcknowledgeTransfer OCTET STRING (CONTAINING PathSwitchRequestAcknowledgeTransfer),
iE-Extensions ProtocolExtensionContainer { { PDUSessionResourceSwitchedItem-ExtIEs} } OPTIONAL,
...
}
PDUSessionResourceSwitchedItem-ExtIEs NGAP-PROTOCOL-EXTENSION ::= {
...
}
PDUSessionResourceToBeSwitchedDLList ::= SEQUENCE (SIZE(1..maxnoofPDUSessions)) OF PDUSessionResourceToBeSwitchedDLItem
PDUSessionResourceToBeSwitchedDLItem ::= SEQUENCE {
pDUSessionID PDUSessionID,
pathSwitchRequestTransfer OCTET STRING (CONTAINING PathSwitchRequestTransfer),
iE-Extensions ProtocolExtensionContainer { { PDUSessionResourceToBeSwitchedDLItem-ExtIEs} } OPTIONAL,
...
}
PDUSessionResourceToBeSwitchedDLItem-ExtIEs NGAP-PROTOCOL-EXTENSION ::= {
...
}
PDUSessionResourceToReleaseListHOCmd ::= SEQUENCE (SIZE(1..maxnoofPDUSessions)) OF PDUSessionResourceToReleaseItemHOCmd
PDUSessionResourceToReleaseItemHOCmd ::= SEQUENCE {
pDUSessionID PDUSessionID,
handoverPreparationUnsuccessfulTransfer OCTET STRING (CONTAINING HandoverPreparationUnsuccessfulTransfer),
iE-Extensions ProtocolExtensionContainer { {PDUSessionResourceToReleaseItemHOCmd-ExtIEs} } OPTIONAL,
...
}
PDUSessionResourceToReleaseItemHOCmd-ExtIEs NGAP-PROTOCOL-EXTENSION ::= {
...
}
PDUSessionResourceToReleaseListRelCmd ::= SEQUENCE (SIZE(1..maxnoofPDUSessions)) OF PDUSessionResourceToReleaseItemRelCmd
PDUSessionResourceToReleaseItemRelCmd ::= SEQUENCE {
pDUSessionID PDUSessionID,
pDUSessionResourceReleaseCommandTransfer OCTET STRING (CONTAINING PDUSessionResourceReleaseCommandTransfer),
iE-Extensions ProtocolExtensionContainer { {PDUSessionResourceToReleaseItemRelCmd-ExtIEs} } OPTIONAL,
...
}
PDUSessionResourceToReleaseItemRelCmd-ExtIEs NGAP-PROTOCOL-EXTENSION ::= {
...
}
PDUSessionType ::= ENUMERATED {
ipv4,
ipv6,
ipv4v6,
ethernet,
unstructured,
...
}
PDUSessionUsageReport ::= SEQUENCE {
rATType ENUMERATED {nr, eutra, ...},
pDUSessionTimedReportList VolumeTimedReportList,
iE-Extensions ProtocolExtensionContainer { {PDUSessionUsageReport-ExtIEs} } OPTIONAL,
...
}
PDUSessionUsageReport-ExtIEs NGAP-PROTOCOL-EXTENSION ::= {
...
}
PeriodicRegistrationUpdateTimer ::= BIT STRING (SIZE(8))
PLMNIdentity ::= OCTET STRING (SIZE(3))
PLMNSupportList ::= SEQUENCE (SIZE(1..maxnoofPLMNs)) OF PLMNSupportItem
PLMNSupportItem ::= SEQUENCE {
pLMNIdentity PLMNIdentity,
sliceSupportList SliceSupportList,
iE-Extensions ProtocolExtensionContainer { {PLMNSupportItem-ExtIEs} } OPTIONAL,
...
}
PLMNSupportItem-ExtIEs NGAP-PROTOCOL-EXTENSION ::= {
...
}
PortNumber ::= OCTET STRING (SIZE(2))
Pre-emptionCapability ::= ENUMERATED {
shall-not-trigger-pre-emption,
may-trigger-pre-emption,
...
}
Pre-emptionVulnerability ::= ENUMERATED {
not-pre-emptable,
pre-emptable,
...
}
PriorityLevelARP ::= INTEGER (1..15)
PriorityLevelQos ::= INTEGER (1..127, ...)
PWSFailedCellIDList ::= CHOICE {
eUTRA-CGI-PWSFailedList EUTRA-CGIList,
nR-CGI-PWSFailedList NR-CGIList,
choice-Extensions ProtocolIE-SingleContainer { {PWSFailedCellIDList-ExtIEs} }
}
PWSFailedCellIDList-ExtIEs NGAP-PROTOCOL-IES ::= {
...
}
-- Q
QosCharacteristics ::= CHOICE {
nonDynamic5QI NonDynamic5QIDescriptor,
dynamic5QI Dynamic5QIDescriptor,
choice-Extensions ProtocolIE-SingleContainer { {QosCharacteristics-ExtIEs} }
}
QosCharacteristics-ExtIEs NGAP-PROTOCOL-IES ::= {
...
}
QosFlowAcceptedList ::= SEQUENCE (SIZE(1..maxnoofQosFlows)) OF QosFlowAcceptedItem
QosFlowAcceptedItem ::= SEQUENCE {
qosFlowIdentifier QosFlowIdentifier,
iE-Extensions ProtocolExtensionContainer { {QosFlowAcceptedItem-ExtIEs} } OPTIONAL,
...
}
QosFlowAcceptedItem-ExtIEs NGAP-PROTOCOL-EXTENSION ::= {
...
}
QosFlowAddOrModifyRequestList ::= SEQUENCE (SIZE(1..maxnoofQosFlows)) OF QosFlowAddOrModifyRequestItem
QosFlowAddOrModifyRequestItem ::= SEQUENCE {
qosFlowIdentifier QosFlowIdentifier,
qosFlowLevelQosParameters QosFlowLevelQosParameters OPTIONAL,
e-RAB-ID E-RAB-ID OPTIONAL,
iE-Extensions ProtocolExtensionContainer { {QosFlowAddOrModifyRequestItem-ExtIEs} } OPTIONAL,
...
}
QosFlowAddOrModifyRequestItem-ExtIEs NGAP-PROTOCOL-EXTENSION ::= {
...
}
QosFlowAddOrModifyResponseList ::= SEQUENCE (SIZE(1..maxnoofQosFlows)) OF QosFlowAddOrModifyResponseItem
QosFlowAddOrModifyResponseItem ::= SEQUENCE {
qosFlowIdentifier QosFlowIdentifier,
iE-Extensions ProtocolExtensionContainer { {QosFlowAddOrModifyResponseItem-ExtIEs} } OPTIONAL,
...
}
QosFlowAddOrModifyResponseItem-ExtIEs NGAP-PROTOCOL-EXTENSION ::= {
...
}
QosFlowIdentifier ::= INTEGER (0..63, ...)
QosFlowInformationList ::= SEQUENCE (SIZE(1..maxnoofQosFlows)) OF QosFlowInformationItem
QosFlowInformationItem ::= SEQUENCE {
qosFlowIdentifier QosFlowIdentifier,
dLForwarding DLForwarding OPTIONAL,
iE-Extensions ProtocolExtensionContainer { {QosFlowInformationItem-ExtIEs} } OPTIONAL,
...
}
QosFlowInformationItem-ExtIEs NGAP-PROTOCOL-EXTENSION ::= {
{ID id-ULForwarding CRITICALITY reject EXTENSION ULForwarding PRESENCE optional},
...
}
QosFlowLevelQosParameters ::= SEQUENCE {
qosCharacteristics QosCharacteristics,
allocationAndRetentionPriority AllocationAndRetentionPriority,
gBR-QosInformation GBR-QosInformation OPTIONAL,
reflectiveQosAttribute ReflectiveQosAttribute OPTIONAL,
additionalQosFlowInformation AdditionalQosFlowInformation OPTIONAL,
iE-Extensions ProtocolExtensionContainer { {QosFlowLevelQosParameters-ExtIEs} } OPTIONAL,
...
}
QosFlowLevelQosParameters-ExtIEs NGAP-PROTOCOL-EXTENSION ::= {
...
}
QosFlowListWithCause ::= SEQUENCE (SIZE(1..maxnoofQosFlows)) OF QosFlowWithCauseItem
QosFlowWithCauseItem ::= SEQUENCE {
qosFlowIdentifier QosFlowIdentifier,
cause Cause,
iE-Extensions ProtocolExtensionContainer { {QosFlowWithCauseItem-ExtIEs} } OPTIONAL,
...
}
QosFlowWithCauseItem-ExtIEs NGAP-PROTOCOL-EXTENSION ::= {
...
}
QosFlowModifyConfirmList ::= SEQUENCE (SIZE(1..maxnoofQosFlows)) OF QosFlowModifyConfirmItem
QosFlowModifyConfirmItem ::= SEQUENCE {
qosFlowIdentifier QosFlowIdentifier,
iE-Extensions ProtocolExtensionContainer { {QosFlowModifyConfirmItem-ExtIEs} } OPTIONAL,
...
}
QosFlowModifyConfirmItem-ExtIEs NGAP-PROTOCOL-EXTENSION ::= {
...
}
QosFlowNotifyList ::= SEQUENCE (SIZE(1..maxnoofQosFlows)) OF QosFlowNotifyItem
QosFlowNotifyItem ::= SEQUENCE {
qosFlowIdentifier QosFlowIdentifier,
notificationCause NotificationCause,
iE-Extensions ProtocolExtensionContainer { {QosFlowNotifyItem-ExtIEs} } OPTIONAL,
...
}
QosFlowNotifyItem-ExtIEs NGAP-PROTOCOL-EXTENSION ::= {
...
}
QosFlowPerTNLInformation ::= SEQUENCE {
uPTransportLayerInformation UPTransportLayerInformation,
associatedQosFlowList AssociatedQosFlowList,
iE-Extensions ProtocolExtensionContainer { { QosFlowPerTNLInformation-ExtIEs} } OPTIONAL,
...
}
QosFlowPerTNLInformation-ExtIEs NGAP-PROTOCOL-EXTENSION ::= {
...
}
QosFlowPerTNLInformationList ::= SEQUENCE (SIZE(1..maxnoofMultiConnectivityMinusOne)) OF QosFlowPerTNLInformationItem
QosFlowPerTNLInformationItem ::= SEQUENCE {
qosFlowPerTNLInformation QosFlowPerTNLInformation,
iE-Extensions ProtocolExtensionContainer { { QosFlowPerTNLInformationItem-ExtIEs} } OPTIONAL,
...
}
QosFlowPerTNLInformationItem-ExtIEs NGAP-PROTOCOL-EXTENSION ::= {
...
}
QosFlowSetupRequestList ::= SEQUENCE (SIZE(1..maxnoofQosFlows)) OF QosFlowSetupRequestItem
QosFlowSetupRequestItem ::= SEQUENCE {
qosFlowIdentifier QosFlowIdentifier,
qosFlowLevelQosParameters QosFlowLevelQosParameters,
e-RAB-ID E-RAB-ID OPTIONAL,
iE-Extensions ProtocolExtensionContainer { {QosFlowSetupRequestItem-ExtIEs} } OPTIONAL,
...
}
QosFlowSetupRequestItem-ExtIEs NGAP-PROTOCOL-EXTENSION ::= {
...
}
QosFlowListWithDataForwarding ::= SEQUENCE (SIZE(1..maxnoofQosFlows)) OF QosFlowItemWithDataForwarding
QosFlowItemWithDataForwarding ::= SEQUENCE {
qosFlowIdentifier QosFlowIdentifier,
dataForwardingAccepted DataForwardingAccepted OPTIONAL,
iE-Extensions ProtocolExtensionContainer { {QosFlowItemWithDataForwarding-ExtIEs} } OPTIONAL,
...
}
QosFlowItemWithDataForwarding-ExtIEs NGAP-PROTOCOL-EXTENSION ::= {
...
}
QosFlowSetupResponseListSURes ::= SEQUENCE (SIZE(1..maxnoofQosFlows)) OF QosFlowSetupResponseItemSURes
QosFlowSetupResponseItemSURes ::= SEQUENCE {
qosFlowIdentifier QosFlowIdentifier,
iE-Extensions ProtocolExtensionContainer { {QosFlowSetupResponseItemSURes-ExtIEs} } OPTIONAL,
...
}
QosFlowSetupResponseItemSURes-ExtIEs NGAP-PROTOCOL-EXTENSION ::= {
...
}
QosFlowToBeForwardedList ::= SEQUENCE (SIZE(1..maxnoofQosFlows)) OF QosFlowToBeForwardedItem
QosFlowToBeForwardedItem ::= SEQUENCE {
qosFlowIdentifier QosFlowIdentifier,
iE-Extensions ProtocolExtensionContainer { {QosFlowToBeForwardedItem-ExtIEs} } OPTIONAL,
...
}
QosFlowToBeForwardedItem-ExtIEs NGAP-PROTOCOL-EXTENSION ::= {
...
}
QoSFlowsUsageReportList ::= SEQUENCE (SIZE(1..maxnoofQosFlows)) OF QoSFlowsUsageReport-Item
QoSFlowsUsageReport-Item ::= SEQUENCE {
qosFlowIdentifier QosFlowIdentifier,
rATType ENUMERATED {nr, eutra, ...},
qoSFlowsTimedReportList VolumeTimedReportList,
iE-Extensions ProtocolExtensionContainer { {QoSFlowsUsageReport-Item-ExtIEs} } OPTIONAL,
...
}
QoSFlowsUsageReport-Item-ExtIEs NGAP-PROTOCOL-EXTENSION ::= {
...
}
-- R
RANNodeName ::= PrintableString (SIZE(1..150, ...))
RANPagingPriority ::= INTEGER (1..256)
RANStatusTransfer-TransparentContainer ::= SEQUENCE {
dRBsSubjectToStatusTransferList DRBsSubjectToStatusTransferList,
iE-Extensions ProtocolExtensionContainer { {RANStatusTransfer-TransparentContainer-ExtIEs} } OPTIONAL,
...
}
RANStatusTransfer-TransparentContainer-ExtIEs NGAP-PROTOCOL-EXTENSION ::= {
...
}
RAN-UE-NGAP-ID ::= INTEGER (0..4294967295)
RATRestrictions ::= SEQUENCE (SIZE(1..maxnoofEPLMNsPlusOne)) OF RATRestrictions-Item
RATRestrictions-Item ::= SEQUENCE {
pLMNIdentity PLMNIdentity,
rATRestrictionInformation RATRestrictionInformation,
iE-Extensions ProtocolExtensionContainer { {RATRestrictions-Item-ExtIEs} } OPTIONAL,
...
}
RATRestrictions-Item-ExtIEs NGAP-PROTOCOL-EXTENSION ::= {
...
}
RATRestrictionInformation ::= BIT STRING (SIZE(8, ...))
RecommendedCellsForPaging ::= SEQUENCE {
recommendedCellList RecommendedCellList,
iE-Extensions ProtocolExtensionContainer { {RecommendedCellsForPaging-ExtIEs} } OPTIONAL,
...
}
RecommendedCellsForPaging-ExtIEs NGAP-PROTOCOL-EXTENSION ::= {
...
}
RecommendedCellList ::= SEQUENCE (SIZE(1..maxnoofRecommendedCells)) OF RecommendedCellItem
RecommendedCellItem ::= SEQUENCE {
nGRAN-CGI NGRAN-CGI,
timeStayedInCell INTEGER (0..4095) OPTIONAL,
iE-Extensions ProtocolExtensionContainer { {RecommendedCellItem-ExtIEs} } OPTIONAL,
...
}
RecommendedCellItem-ExtIEs NGAP-PROTOCOL-EXTENSION ::= {
...
}
RecommendedRANNodesForPaging ::= SEQUENCE {
recommendedRANNodeList RecommendedRANNodeList,
iE-Extensions ProtocolExtensionContainer { {RecommendedRANNodesForPaging-ExtIEs} } OPTIONAL,
...
}
RecommendedRANNodesForPaging-ExtIEs NGAP-PROTOCOL-EXTENSION ::= {
...
}
RecommendedRANNodeList::= SEQUENCE (SIZE(1..maxnoofRecommendedRANNodes)) OF RecommendedRANNodeItem
RecommendedRANNodeItem ::= SEQUENCE {
aMFPagingTarget AMFPagingTarget,
iE-Extensions ProtocolExtensionContainer { {RecommendedRANNodeItem-ExtIEs} } OPTIONAL,
...
}
RecommendedRANNodeItem-ExtIEs NGAP-PROTOCOL-EXTENSION ::= {
...
}
RedirectionVoiceFallback ::= ENUMERATED {
possible,
not-possible,
...
}
ReflectiveQosAttribute ::= ENUMERATED {
subject-to,
...
}
ReferenceID ::= INTEGER (1..64, ...)
RelativeAMFCapacity ::= INTEGER (0..255)
ReportArea ::= ENUMERATED {
cell,
...
}
RepetitionPeriod ::= INTEGER (0..131071)
ResetAll ::= ENUMERATED {
reset-all,
...
}
ResetType ::= CHOICE {
nG-Interface ResetAll,
partOfNG-Interface UE-associatedLogicalNG-connectionList,
choice-Extensions ProtocolIE-SingleContainer { {ResetType-ExtIEs} }
}
ResetType-ExtIEs NGAP-PROTOCOL-IES ::= {
...
}
RoutingID ::= OCTET STRING
RRCContainer ::= OCTET STRING
RRCEstablishmentCause ::= ENUMERATED {
emergency,
highPriorityAccess,
mt-Access,
mo-Signalling,
mo-Data,
mo-VoiceCall,
mo-VideoCall,
mo-SMS,
mps-PriorityAccess,
mcs-PriorityAccess,
...,
notAvailable
}
RRCInactiveTransitionReportRequest ::= ENUMERATED {
subsequent-state-transition-report,
single-rrc-connected-state-report,
cancel-report,
...
}
RRCState ::= ENUMERATED {
inactive,
connected,
...
}
-- S
SCTP-TLAs ::= SEQUENCE (SIZE(1..maxnoofXnTLAs)) OF TransportLayerAddress
SD ::= OCTET STRING (SIZE(3))
SecondaryRATUsageInformation ::= SEQUENCE {
pDUSessionUsageReport PDUSessionUsageReport OPTIONAL,
qosFlowsUsageReportList QoSFlowsUsageReportList OPTIONAL,
iE-Extension ProtocolExtensionContainer { {SecondaryRATUsageInformation-ExtIEs} } OPTIONAL,
...
}
SecondaryRATUsageInformation-ExtIEs NGAP-PROTOCOL-EXTENSION ::= {
...
}
SecondaryRATDataUsageReportTransfer ::= SEQUENCE {
secondaryRATUsageInformation SecondaryRATUsageInformation OPTIONAL,
iE-Extensions ProtocolExtensionContainer { {SecondaryRATDataUsageReportTransfer-ExtIEs} } OPTIONAL,
...
}
SecondaryRATDataUsageReportTransfer-ExtIEs NGAP-PROTOCOL-EXTENSION ::= {
...
}
SecurityContext ::= SEQUENCE {
nextHopChainingCount NextHopChainingCount,
nextHopNH SecurityKey,
iE-Extensions ProtocolExtensionContainer { {SecurityContext-ExtIEs} } OPTIONAL,
...
}
SecurityContext-ExtIEs NGAP-PROTOCOL-EXTENSION ::= {
...
}
SecurityIndication ::= SEQUENCE {
integrityProtectionIndication IntegrityProtectionIndication,
confidentialityProtectionIndication ConfidentialityProtectionIndication,
maximumIntegrityProtectedDataRate-UL MaximumIntegrityProtectedDataRate OPTIONAL,
-- The above IE shall be present if integrity protection is required or preferred
iE-Extensions ProtocolExtensionContainer { {SecurityIndication-ExtIEs} } OPTIONAL,
...
}
SecurityIndication-ExtIEs NGAP-PROTOCOL-EXTENSION ::= {
{ ID id-MaximumIntegrityProtectedDataRate-DL CRITICALITY ignore EXTENSION MaximumIntegrityProtectedDataRate PRESENCE optional },
...
}
SecurityKey ::= BIT STRING (SIZE(256))
SecurityResult ::= SEQUENCE {
integrityProtectionResult IntegrityProtectionResult,
confidentialityProtectionResult ConfidentialityProtectionResult,
iE-Extensions ProtocolExtensionContainer { {SecurityResult-ExtIEs} } OPTIONAL,
...
}
SecurityResult-ExtIEs NGAP-PROTOCOL-EXTENSION ::= {
...
}
SerialNumber ::= BIT STRING (SIZE(16))
ServedGUAMIList ::= SEQUENCE (SIZE(1..maxnoofServedGUAMIs)) OF ServedGUAMIItem
ServedGUAMIItem ::= SEQUENCE {
gUAMI GUAMI,
backupAMFName AMFName OPTIONAL,
iE-Extensions ProtocolExtensionContainer { {ServedGUAMIItem-ExtIEs} } OPTIONAL,
...
}
ServedGUAMIItem-ExtIEs NGAP-PROTOCOL-EXTENSION ::= {
...
}
ServiceAreaInformation ::= SEQUENCE (SIZE(1.. maxnoofEPLMNsPlusOne)) OF ServiceAreaInformation-Item
ServiceAreaInformation-Item ::= SEQUENCE {
pLMNIdentity PLMNIdentity,
allowedTACs AllowedTACs OPTIONAL,
notAllowedTACs NotAllowedTACs OPTIONAL,
iE-Extensions ProtocolExtensionContainer { {ServiceAreaInformation-Item-ExtIEs} } OPTIONAL,
...
}
ServiceAreaInformation-Item-ExtIEs NGAP-PROTOCOL-EXTENSION ::= {
...
}
SliceOverloadList ::= SEQUENCE (SIZE(1..maxnoofSliceItems)) OF SliceOverloadItem
SliceOverloadItem ::= SEQUENCE {
s-NSSAI S-NSSAI,
iE-Extensions ProtocolExtensionContainer { {SliceOverloadItem-ExtIEs} } OPTIONAL,
...
}
SliceOverloadItem-ExtIEs NGAP-PROTOCOL-EXTENSION ::= {
...
}
SliceSupportList ::= SEQUENCE (SIZE(1..maxnoofSliceItems)) OF SliceSupportItem
SliceSupportItem ::= SEQUENCE {
s-NSSAI S-NSSAI,
iE-Extensions ProtocolExtensionContainer { {SliceSupportItem-ExtIEs} } OPTIONAL,
...
}
SliceSupportItem-ExtIEs NGAP-PROTOCOL-EXTENSION ::= {
...
}
S-NSSAI ::= SEQUENCE {
sST SST,
sD SD OPTIONAL,
iE-Extensions ProtocolExtensionContainer { { S-NSSAI-ExtIEs} } OPTIONAL,
...
}
S-NSSAI-ExtIEs NGAP-PROTOCOL-EXTENSION ::= {
...
}
SONConfigurationTransfer ::= SEQUENCE {
targetRANNodeID TargetRANNodeID,
sourceRANNodeID SourceRANNodeID,
sONInformation SONInformation,
xnTNLConfigurationInfo XnTNLConfigurationInfo OPTIONAL,
-- The above IE shall be present if the SON Information IE contains the SON Information Request IE set to “Xn TNL Configuration Info”
iE-Extensions ProtocolExtensionContainer { {SONConfigurationTransfer-ExtIEs} } OPTIONAL,
...
}
SONConfigurationTransfer-ExtIEs NGAP-PROTOCOL-EXTENSION ::= {
...
}
SONInformation ::= CHOICE {
sONInformationRequest SONInformationRequest,
sONInformationReply SONInformationReply,
choice-Extensions ProtocolIE-SingleContainer { {SONInformation-ExtIEs} }
}
SONInformation-ExtIEs NGAP-PROTOCOL-IES ::= {
...
}
SONInformationReply ::= SEQUENCE {
xnTNLConfigurationInfo XnTNLConfigurationInfo OPTIONAL,
iE-Extensions ProtocolExtensionContainer { {SONInformationReply-ExtIEs} } OPTIONAL,
...
}
SONInformationReply-ExtIEs NGAP-PROTOCOL-EXTENSION ::= {
...
}
SONInformationRequest ::= ENUMERATED {
xn-TNL-configuration-info,
...
}
SourceNGRANNode-ToTargetNGRANNode-TransparentContainer ::= SEQUENCE {
rRCContainer RRCContainer,
pDUSessionResourceInformationList PDUSessionResourceInformationList OPTIONAL,
e-RABInformationList E-RABInformationList OPTIONAL,
targetCell-ID NGRAN-CGI,
indexToRFSP IndexToRFSP OPTIONAL,
uEHistoryInformation UEHistoryInformation,
iE-Extensions ProtocolExtensionContainer { {SourceNGRANNode-ToTargetNGRANNode-TransparentContainer-ExtIEs} } OPTIONAL,
...
}
SourceNGRANNode-ToTargetNGRANNode-TransparentContainer-ExtIEs NGAP-PROTOCOL-EXTENSION ::= {
...
}
SourceOfUEActivityBehaviourInformation ::= ENUMERATED {
subscription-information,
statistics,
...
}
SourceRANNodeID ::= SEQUENCE {
globalRANNodeID GlobalRANNodeID,
selectedTAI TAI,
iE-Extensions ProtocolExtensionContainer { {SourceRANNodeID-ExtIEs} } OPTIONAL,
...
}
SourceRANNodeID-ExtIEs NGAP-PROTOCOL-EXTENSION ::= {
...
}
SourceToTarget-TransparentContainer ::= OCTET STRING
-- This IE includes a transparent container from the source RAN node to the target RAN node.
-- The octets of the OCTET STRING are encoded according to the specifications of the target system.
SourceToTarget-AMFInformationReroute ::= SEQUENCE {
configuredNSSAI ConfiguredNSSAI OPTIONAL,
rejectedNSSAIinPLMN RejectedNSSAIinPLMN OPTIONAL,
rejectedNSSAIinTA RejectedNSSAIinTA OPTIONAL,
iE-Extensions ProtocolExtensionContainer { {SourceToTarget-AMFInformationReroute-ExtIEs} } OPTIONAL,
...
}
SourceToTarget-AMFInformationReroute-ExtIEs NGAP-PROTOCOL-EXTENSION ::= {
...
}
-- This IE includes information from the source Core node to the target Core node for reroute information provide by NSSF.
-- The octets of the OCTET STRING are encoded according to the specifications of the Core network.
ConfiguredNSSAI ::= OCTET STRING (SIZE(128))
RejectedNSSAIinPLMN ::= OCTET STRING (SIZE(32))
RejectedNSSAIinTA ::= OCTET STRING (SIZE(32))
SST ::= OCTET STRING (SIZE(1))
SupportedTAList ::= SEQUENCE (SIZE(1..maxnoofTACs)) OF SupportedTAItem
SupportedTAItem ::= SEQUENCE {
tAC TAC,
broadcastPLMNList BroadcastPLMNList,
iE-Extensions ProtocolExtensionContainer { {SupportedTAItem-ExtIEs} } OPTIONAL,
...
}
SupportedTAItem-ExtIEs NGAP-PROTOCOL-EXTENSION ::= {
...
}
-- T
TAC ::= OCTET STRING (SIZE(3))
TAI ::= SEQUENCE {
pLMNIdentity PLMNIdentity,
tAC TAC,
iE-Extensions ProtocolExtensionContainer { {TAI-ExtIEs} } OPTIONAL,
...
}
TAI-ExtIEs NGAP-PROTOCOL-EXTENSION ::= {
...
}
TAIBroadcastEUTRA ::= SEQUENCE (SIZE(1..maxnoofTAIforWarning)) OF TAIBroadcastEUTRA-Item
TAIBroadcastEUTRA-Item ::= SEQUENCE {
tAI TAI,
completedCellsInTAI-EUTRA CompletedCellsInTAI-EUTRA,
iE-Extensions ProtocolExtensionContainer { {TAIBroadcastEUTRA-Item-ExtIEs} } OPTIONAL,
...
}
TAIBroadcastEUTRA-Item-ExtIEs NGAP-PROTOCOL-EXTENSION ::= {
...
}
TAIBroadcastNR ::= SEQUENCE (SIZE(1..maxnoofTAIforWarning)) OF TAIBroadcastNR-Item
TAIBroadcastNR-Item ::= SEQUENCE {
tAI TAI,
completedCellsInTAI-NR CompletedCellsInTAI-NR,
iE-Extensions ProtocolExtensionContainer { {TAIBroadcastNR-Item-ExtIEs} } OPTIONAL,
...
}
TAIBroadcastNR-Item-ExtIEs NGAP-PROTOCOL-EXTENSION ::= {
...
}
TAICancelledEUTRA ::= SEQUENCE (SIZE(1..maxnoofTAIforWarning)) OF TAICancelledEUTRA-Item
TAICancelledEUTRA-Item ::= SEQUENCE {
tAI TAI,
cancelledCellsInTAI-EUTRA CancelledCellsInTAI-EUTRA,
iE-Extensions ProtocolExtensionContainer { {TAICancelledEUTRA-Item-ExtIEs} } OPTIONAL,
...
}
TAICancelledEUTRA-Item-ExtIEs NGAP-PROTOCOL-EXTENSION ::= {
...
}
TAICancelledNR ::= SEQUENCE (SIZE(1..maxnoofTAIforWarning)) OF TAICancelledNR-Item
TAICancelledNR-Item ::= SEQUENCE {
tAI TAI,
cancelledCellsInTAI-NR CancelledCellsInTAI-NR,
iE-Extensions ProtocolExtensionContainer { {TAICancelledNR-Item-ExtIEs} } OPTIONAL,
...
}
TAICancelledNR-Item-ExtIEs NGAP-PROTOCOL-EXTENSION ::= {
...
}
TAIListForInactive ::= SEQUENCE (SIZE(1..maxnoofTAIforInactive)) OF TAIListForInactiveItem
TAIListForInactiveItem ::= SEQUENCE {
tAI TAI,
iE-Extensions ProtocolExtensionContainer { {TAIListForInactiveItem-ExtIEs} } OPTIONAL,
...
}
TAIListForInactiveItem-ExtIEs NGAP-PROTOCOL-EXTENSION ::= {
...
}
TAIListForPaging ::= SEQUENCE (SIZE(1..maxnoofTAIforPaging)) OF TAIListForPagingItem
TAIListForPagingItem ::= SEQUENCE {
tAI TAI,
iE-Extensions ProtocolExtensionContainer { {TAIListForPagingItem-ExtIEs} } OPTIONAL,
...
}
TAIListForPagingItem-ExtIEs NGAP-PROTOCOL-EXTENSION ::= {
...
}
TAIListForRestart ::= SEQUENCE (SIZE(1..maxnoofTAIforRestart)) OF TAI
TAIListForWarning ::= SEQUENCE (SIZE(1..maxnoofTAIforWarning)) OF TAI
TargeteNB-ID ::= SEQUENCE {
globalENB-ID GlobalNgENB-ID,
selected-EPS-TAI EPS-TAI,
iE-Extensions ProtocolExtensionContainer { {TargeteNB-ID-ExtIEs} } OPTIONAL,
...
}
TargeteNB-ID-ExtIEs NGAP-PROTOCOL-EXTENSION ::= {
...
}
TargetID ::= CHOICE {
targetRANNodeID TargetRANNodeID,
targeteNB-ID TargeteNB-ID,
choice-Extensions ProtocolIE-SingleContainer { {TargetID-ExtIEs} }
}
TargetID-ExtIEs NGAP-PROTOCOL-IES ::= {
...
}
TargetNGRANNode-ToSourceNGRANNode-TransparentContainer ::= SEQUENCE {
rRCContainer RRCContainer,
iE-Extensions ProtocolExtensionContainer { {TargetNGRANNode-ToSourceNGRANNode-TransparentContainer-ExtIEs} } OPTIONAL,
...
}
TargetNGRANNode-ToSourceNGRANNode-TransparentContainer-ExtIEs NGAP-PROTOCOL-EXTENSION ::= {
...
}
TargetRANNodeID ::= SEQUENCE {
globalRANNodeID GlobalRANNodeID,
selectedTAI TAI,
iE-Extensions ProtocolExtensionContainer { {TargetRANNodeID-ExtIEs} } OPTIONAL,
...
}
TargetRANNodeID-ExtIEs NGAP-PROTOCOL-EXTENSION ::= {
...
}
TargetToSource-TransparentContainer ::= OCTET STRING
-- This IE includes a transparent container from the target RAN node to the source RAN node.
-- The octets of the OCTET STRING are encoded according to the specifications of the target system.
TimerApproachForGUAMIRemoval ::= ENUMERATED {
apply-timer,
...
}
TimeStamp ::= OCTET STRING (SIZE(4))
TimeToWait ::= ENUMERATED {v1s, v2s, v5s, v10s, v20s, v60s, ...}
TimeUEStayedInCell ::= INTEGER (0..4095)
TimeUEStayedInCellEnhancedGranularity ::= INTEGER (0..40950)
TNLAddressWeightFactor ::= INTEGER (0..255)
TNLAssociationList ::= SEQUENCE (SIZE(1..maxnoofTNLAssociations)) OF TNLAssociationItem
TNLAssociationItem ::= SEQUENCE {
tNLAssociationAddress CPTransportLayerInformation,
cause Cause,
iE-Extensions ProtocolExtensionContainer { {TNLAssociationItem-ExtIEs} } OPTIONAL,
...
}
TNLAssociationItem-ExtIEs NGAP-PROTOCOL-EXTENSION ::= {
...
}
TNLAssociationUsage ::= ENUMERATED {
ue,
non-ue,
both,
...
}
TraceActivation ::= SEQUENCE {
nGRANTraceID NGRANTraceID,
interfacesToTrace InterfacesToTrace,
traceDepth TraceDepth,
traceCollectionEntityIPAddress TransportLayerAddress,
iE-Extensions ProtocolExtensionContainer { {TraceActivation-ExtIEs} } OPTIONAL,
...
}
TraceActivation-ExtIEs NGAP-PROTOCOL-EXTENSION ::= {
...
}
TraceDepth ::= ENUMERATED {
minimum,
medium,
maximum,
minimumWithoutVendorSpecificExtension,
mediumWithoutVendorSpecificExtension,
maximumWithoutVendorSpecificExtension,
...
}
TrafficLoadReductionIndication ::= INTEGER (1..99)
TransportLayerAddress ::= BIT STRING (SIZE(1..160, ...))
TypeOfError ::= ENUMERATED {
not-understood,
missing,
...
}
-- U
UEAggregateMaximumBitRate ::= SEQUENCE {
uEAggregateMaximumBitRateDL BitRate,
uEAggregateMaximumBitRateUL BitRate,
iE-Extensions ProtocolExtensionContainer { {UEAggregateMaximumBitRate-ExtIEs} } OPTIONAL,
...
}
UEAggregateMaximumBitRate-ExtIEs NGAP-PROTOCOL-EXTENSION ::= {
...
}
UE-associatedLogicalNG-connectionList ::= SEQUENCE (SIZE(1..maxnoofNGConnectionsToReset)) OF UE-associatedLogicalNG-connectionItem
UE-associatedLogicalNG-connectionItem ::= SEQUENCE {
aMF-UE-NGAP-ID AMF-UE-NGAP-ID OPTIONAL,
rAN-UE-NGAP-ID RAN-UE-NGAP-ID OPTIONAL,
iE-Extensions ProtocolExtensionContainer { {UE-associatedLogicalNG-connectionItem-ExtIEs} } OPTIONAL,
...
}
UE-associatedLogicalNG-connectionItem-ExtIEs NGAP-PROTOCOL-EXTENSION ::= {
...}
UEContextRequest ::= ENUMERATED {requested, ...}
UEHistoryInformation ::= SEQUENCE (SIZE(1..maxnoofCellsinUEHistoryInfo)) OF LastVisitedCellItem
UEIdentityIndexValue ::= CHOICE {
indexLength10 BIT STRING (SIZE(10)),
choice-Extensions ProtocolIE-SingleContainer { {UEIdentityIndexValue-ExtIEs} }
}
UEIdentityIndexValue-ExtIEs NGAP-PROTOCOL-IES ::= {
...
}
UE-NGAP-IDs ::= CHOICE {
uE-NGAP-ID-pair UE-NGAP-ID-pair,
aMF-UE-NGAP-ID AMF-UE-NGAP-ID,
choice-Extensions ProtocolIE-SingleContainer { {UE-NGAP-IDs-ExtIEs} }
}
UE-NGAP-IDs-ExtIEs NGAP-PROTOCOL-IES ::= {
...
}
UE-NGAP-ID-pair ::= SEQUENCE{
aMF-UE-NGAP-ID AMF-UE-NGAP-ID,
rAN-UE-NGAP-ID RAN-UE-NGAP-ID,
iE-Extensions ProtocolExtensionContainer { {UE-NGAP-ID-pair-ExtIEs} } OPTIONAL,
...
}
UE-NGAP-ID-pair-ExtIEs NGAP-PROTOCOL-EXTENSION ::= {
...
}
UEPagingIdentity ::= CHOICE {
fiveG-S-TMSI FiveG-S-TMSI,
choice-Extensions ProtocolIE-SingleContainer { {UEPagingIdentity-ExtIEs} }
}
UEPagingIdentity-ExtIEs NGAP-PROTOCOL-IES ::= {
...
}
UEPresence ::= ENUMERATED {in, out, unknown, ...}
UEPresenceInAreaOfInterestList ::= SEQUENCE (SIZE(1..maxnoofAoI)) OF UEPresenceInAreaOfInterestItem
UEPresenceInAreaOfInterestItem ::= SEQUENCE {
locationReportingReferenceID LocationReportingReferenceID,
uEPresence UEPresence,
iE-Extensions ProtocolExtensionContainer { {UEPresenceInAreaOfInterestItem-ExtIEs} } OPTIONAL,
...
}
UEPresenceInAreaOfInterestItem-ExtIEs NGAP-PROTOCOL-EXTENSION ::= {
...
}
UERadioCapability ::= OCTET STRING
UERadioCapabilityForPaging ::= SEQUENCE {
uERadioCapabilityForPagingOfNR UERadioCapabilityForPagingOfNR OPTIONAL,
uERadioCapabilityForPagingOfEUTRA UERadioCapabilityForPagingOfEUTRA OPTIONAL,
iE-Extensions ProtocolExtensionContainer { {UERadioCapabilityForPaging-ExtIEs} } OPTIONAL,
...
}
UERadioCapabilityForPaging-ExtIEs NGAP-PROTOCOL-EXTENSION ::= {
...
}
UERadioCapabilityForPagingOfNR ::= OCTET STRING
UERadioCapabilityForPagingOfEUTRA ::= OCTET STRING
UERetentionInformation ::= ENUMERATED {
ues-retained,
...
}
UESecurityCapabilities ::= SEQUENCE {
nRencryptionAlgorithms NRencryptionAlgorithms,
nRintegrityProtectionAlgorithms NRintegrityProtectionAlgorithms,
eUTRAencryptionAlgorithms EUTRAencryptionAlgorithms,
eUTRAintegrityProtectionAlgorithms EUTRAintegrityProtectionAlgorithms,
iE-Extensions ProtocolExtensionContainer { {UESecurityCapabilities-ExtIEs} } OPTIONAL,
...
}
UESecurityCapabilities-ExtIEs NGAP-PROTOCOL-EXTENSION ::= {
...
}
UL-NGU-UP-TNLModifyList ::= SEQUENCE (SIZE(1..maxnoofMultiConnectivity)) OF UL-NGU-UP-TNLModifyItem
UL-NGU-UP-TNLModifyItem ::= SEQUENCE {
uL-NGU-UP-TNLInformation UPTransportLayerInformation,
dL-NGU-UP-TNLInformation UPTransportLayerInformation,
iE-Extensions ProtocolExtensionContainer { {UL-NGU-UP-TNLModifyItem-ExtIEs} } OPTIONAL,
...
}
UL-NGU-UP-TNLModifyItem-ExtIEs NGAP-PROTOCOL-EXTENSION ::= {
...
}
UnavailableGUAMIList ::= SEQUENCE (SIZE(1..maxnoofServedGUAMIs)) OF UnavailableGUAMIItem
UnavailableGUAMIItem ::= SEQUENCE {
gUAMI GUAMI,
timerApproachForGUAMIRemoval TimerApproachForGUAMIRemoval OPTIONAL,
backupAMFName AMFName OPTIONAL,
iE-Extensions ProtocolExtensionContainer { {UnavailableGUAMIItem-ExtIEs} } OPTIONAL,
...
}
UnavailableGUAMIItem-ExtIEs NGAP-PROTOCOL-EXTENSION ::= {
...
}
ULForwarding ::= ENUMERATED {
ul-forwarding-proposed,
...
}
UPTransportLayerInformation ::= CHOICE {
gTPTunnel GTPTunnel,
choice-Extensions ProtocolIE-SingleContainer { {UPTransportLayerInformation-ExtIEs} }
}
UPTransportLayerInformation-ExtIEs NGAP-PROTOCOL-IES ::= {
...
}
UPTransportLayerInformationList ::= SEQUENCE (SIZE(1..maxnoofMultiConnectivityMinusOne)) OF UPTransportLayerInformationItem
UPTransportLayerInformationItem ::= SEQUENCE {
nGU-UP-TNLInformation UPTransportLayerInformation,
iE-Extensions ProtocolExtensionContainer { {UPTransportLayerInformationItem-ExtIEs} } OPTIONAL,
...
}
UPTransportLayerInformationItem-ExtIEs NGAP-PROTOCOL-EXTENSION ::= {
...
}
UPTransportLayerInformationPairList ::= SEQUENCE (SIZE(1..maxnoofMultiConnectivityMinusOne)) OF UPTransportLayerInformationPairItem
UPTransportLayerInformationPairItem ::= SEQUENCE {
uL-NGU-UP-TNLInformation UPTransportLayerInformation,
dL-NGU-UP-TNLInformation UPTransportLayerInformation,
iE-Extensions ProtocolExtensionContainer { {UPTransportLayerInformationPairItem-ExtIEs} } OPTIONAL,
...
}
UPTransportLayerInformationPairItem-ExtIEs NGAP-PROTOCOL-EXTENSION ::= {
...
}
UserLocationInformation ::= CHOICE {
userLocationInformationEUTRA UserLocationInformationEUTRA,
userLocationInformationNR UserLocationInformationNR,
userLocationInformationN3IWF UserLocationInformationN3IWF,
choice-Extensions ProtocolIE-SingleContainer { {UserLocationInformation-ExtIEs} }
}
UserLocationInformation-ExtIEs NGAP-PROTOCOL-IES ::= {
...
}
UserLocationInformationEUTRA ::= SEQUENCE {
eUTRA-CGI EUTRA-CGI,
tAI TAI,
timeStamp TimeStamp OPTIONAL,
iE-Extensions ProtocolExtensionContainer { {UserLocationInformationEUTRA-ExtIEs} } OPTIONAL,
...
}
UserLocationInformationEUTRA-ExtIEs NGAP-PROTOCOL-EXTENSION ::= {
{ ID id-PSCellInformation CRITICALITY ignore EXTENSION NGRAN-CGI PRESENCE optional},
...
}
UserLocationInformationN3IWF ::= SEQUENCE {
iPAddress TransportLayerAddress,
portNumber PortNumber,
iE-Extensions ProtocolExtensionContainer { {UserLocationInformationN3IWF-ExtIEs} } OPTIONAL,
...
}
UserLocationInformationN3IWF-ExtIEs NGAP-PROTOCOL-EXTENSION ::= {
...
}
UserLocationInformationNR ::= SEQUENCE {
nR-CGI NR-CGI,
tAI TAI,
timeStamp TimeStamp OPTIONAL,
iE-Extensions ProtocolExtensionContainer { {UserLocationInformationNR-ExtIEs} } OPTIONAL,
...
}
UserLocationInformationNR-ExtIEs NGAP-PROTOCOL-EXTENSION ::= {
{ ID id-PSCellInformation CRITICALITY ignore EXTENSION NGRAN-CGI PRESENCE optional},
...
}
UserPlaneSecurityInformation ::= SEQUENCE {
securityResult SecurityResult,
securityIndication SecurityIndication,
iE-Extensions ProtocolExtensionContainer { {UserPlaneSecurityInformation-ExtIEs} } OPTIONAL,
...
}
UserPlaneSecurityInformation-ExtIEs NGAP-PROTOCOL-EXTENSION ::= {
...
}
-- V
VolumeTimedReportList ::= SEQUENCE (SIZE(1..maxnoofTimePeriods)) OF VolumeTimedReport-Item
VolumeTimedReport-Item ::= SEQUENCE {
startTimeStamp OCTET STRING (SIZE(4)),
endTimeStamp OCTET STRING (SIZE(4)),
usageCountUL INTEGER (0..18446744073709551615),
usageCountDL INTEGER (0..18446744073709551615),
iE-Extensions ProtocolExtensionContainer { {VolumeTimedReport-Item-ExtIEs} } OPTIONAL,
...
}
VolumeTimedReport-Item-ExtIEs NGAP-PROTOCOL-EXTENSION ::= {
...
}
-- W
WarningAreaCoordinates ::= OCTET STRING (SIZE(1..1024))
WarningAreaList ::= CHOICE {
eUTRA-CGIListForWarning EUTRA-CGIListForWarning,
nR-CGIListForWarning NR-CGIListForWarning,
tAIListForWarning TAIListForWarning,
emergencyAreaIDList EmergencyAreaIDList,
choice-Extensions ProtocolIE-SingleContainer { {WarningAreaList-ExtIEs} }
}
WarningAreaList-ExtIEs NGAP-PROTOCOL-IES ::= {
...
}
WarningMessageContents ::= OCTET STRING (SIZE(1..9600))
WarningSecurityInfo ::= OCTET STRING (SIZE(50))
WarningType ::= OCTET STRING (SIZE(2))
-- X
XnExtTLAs ::= SEQUENCE (SIZE(1..maxnoofXnExtTLAs)) OF XnExtTLA-Item
XnExtTLA-Item ::= SEQUENCE {
iPsecTLA TransportLayerAddress OPTIONAL,
gTP-TLAs XnGTP-TLAs OPTIONAL,
iE-Extensions ProtocolExtensionContainer { {XnExtTLA-Item-ExtIEs} } OPTIONAL,
...
}
XnExtTLA-Item-ExtIEs NGAP-PROTOCOL-EXTENSION ::= {
{ ID id-SCTP-TLAs CRITICALITY ignore EXTENSION SCTP-TLAs PRESENCE optional },
...
}
XnGTP-TLAs ::= SEQUENCE (SIZE(1..maxnoofXnGTP-TLAs)) OF TransportLayerAddress
XnTLAs ::= SEQUENCE (SIZE(1..maxnoofXnTLAs)) OF TransportLayerAddress
XnTNLConfigurationInfo ::= SEQUENCE {
xnTransportLayerAddresses XnTLAs,
xnExtendedTransportLayerAddresses XnExtTLAs OPTIONAL,
iE-Extensions ProtocolExtensionContainer { {XnTNLConfigurationInfo-ExtIEs} } OPTIONAL,
...
}
XnTNLConfigurationInfo-ExtIEs NGAP-PROTOCOL-EXTENSION ::= {
...
}
-- Y
-- Z
END

-- **************************************************************
--
-- Common definitions
--
-- **************************************************************
NGAP-CommonDataTypes {
itu-t (0) identified-organization (4) etsi (0) mobileDomain (0)
ngran-Access (22) modules (3) ngap (1) version1 (1) ngap-CommonDataTypes (3) }
DEFINITIONS AUTOMATIC TAGS ::=
BEGIN
Criticality ::= ENUMERATED { reject, ignore, notify }
Presence ::= ENUMERATED { optional, conditional, mandatory }
PrivateIE-ID ::= CHOICE {
local INTEGER (0..65535),
global OBJECT IDENTIFIER
}
ProcedureCode ::= INTEGER (0..255)
ProtocolExtensionID ::= INTEGER (0..65535)
ProtocolIE-ID ::= INTEGER (0..65535)
TriggeringMessage ::= ENUMERATED { initiating-message, successful-outcome, unsuccessfull-outcome }
END

-- **************************************************************
--
-- Constant definitions
--
-- **************************************************************
NGAP-Constants {
itu-t (0) identified-organization (4) etsi (0) mobileDomain (0)
ngran-Access (22) modules (3) ngap (1) version1 (1) ngap-Constants (4) }
DEFINITIONS AUTOMATIC TAGS ::=
BEGIN
-- **************************************************************
--
-- IE parameter types from other modules.
--
-- **************************************************************
IMPORTS
ProcedureCode,
ProtocolIE-ID
FROM NGAP-CommonDataTypes;
-- **************************************************************
--
-- Elementary Procedures
--
-- **************************************************************
id-AMFConfigurationUpdate ProcedureCode ::= 0
id-AMFStatusIndication ProcedureCode ::= 1
id-CellTrafficTrace ProcedureCode ::= 2
id-DeactivateTrace ProcedureCode ::= 3
id-DownlinkNASTransport ProcedureCode ::= 4
id-DownlinkNonUEAssociatedNRPPaTransport ProcedureCode ::= 5
id-DownlinkRANConfigurationTransfer ProcedureCode ::= 6
id-DownlinkRANStatusTransfer ProcedureCode ::= 7
id-DownlinkUEAssociatedNRPPaTransport ProcedureCode ::= 8
id-ErrorIndication ProcedureCode ::= 9
id-HandoverCancel ProcedureCode ::= 10
id-HandoverNotification ProcedureCode ::= 11
id-HandoverPreparation ProcedureCode ::= 12
id-HandoverResourceAllocation ProcedureCode ::= 13
id-InitialContextSetup ProcedureCode ::= 14
id-InitialUEMessage ProcedureCode ::= 15
id-LocationReportingControl ProcedureCode ::= 16
id-LocationReportingFailureIndication ProcedureCode ::= 17
id-LocationReport ProcedureCode ::= 18
id-NASNonDeliveryIndication ProcedureCode ::= 19
id-NGReset ProcedureCode ::= 20
id-NGSetup ProcedureCode ::= 21
id-OverloadStart ProcedureCode ::= 22
id-OverloadStop ProcedureCode ::= 23
id-Paging ProcedureCode ::= 24
id-PathSwitchRequest ProcedureCode ::= 25
id-PDUSessionResourceModify ProcedureCode ::= 26
id-PDUSessionResourceModifyIndication ProcedureCode ::= 27
id-PDUSessionResourceRelease ProcedureCode ::= 28
id-PDUSessionResourceSetup ProcedureCode ::= 29
id-PDUSessionResourceNotify ProcedureCode ::= 30
id-PrivateMessage ProcedureCode ::= 31
id-PWSCancel ProcedureCode ::= 32
id-PWSFailureIndication ProcedureCode ::= 33
id-PWSRestartIndication ProcedureCode ::= 34
id-RANConfigurationUpdate ProcedureCode ::= 35
id-RerouteNASRequest ProcedureCode ::= 36
id-RRCInactiveTransitionReport ProcedureCode ::= 37
id-TraceFailureIndication ProcedureCode ::= 38
id-TraceStart ProcedureCode ::= 39
id-UEContextModification ProcedureCode ::= 40
id-UEContextRelease ProcedureCode ::= 41
id-UEContextReleaseRequest ProcedureCode ::= 42
id-UERadioCapabilityCheck ProcedureCode ::= 43
id-UERadioCapabilityInfoIndication ProcedureCode ::= 44
id-UETNLABindingRelease ProcedureCode ::= 45
id-UplinkNASTransport ProcedureCode ::= 46
id-UplinkNonUEAssociatedNRPPaTransport ProcedureCode ::= 47
id-UplinkRANConfigurationTransfer ProcedureCode ::= 48
id-UplinkRANStatusTransfer ProcedureCode ::= 49
id-UplinkUEAssociatedNRPPaTransport ProcedureCode ::= 50
id-WriteReplaceWarning ProcedureCode ::= 51
id-SecondaryRATDataUsageReport ProcedureCode ::= 52
-- **************************************************************
--
-- Extension constants
--
-- **************************************************************
maxPrivateIEs INTEGER ::= 65535
maxProtocolExtensions INTEGER ::= 65535
maxProtocolIEs INTEGER ::= 65535
-- **************************************************************
--
-- Lists
--
-- **************************************************************
maxnoofAllowedAreas INTEGER ::= 16
maxnoofAllowedS-NSSAIs INTEGER ::= 8
maxnoofBPLMNs INTEGER ::= 12
maxnoofCellIDforWarning INTEGER ::= 65535
maxnoofCellinAoI INTEGER ::= 256
maxnoofCellinEAI INTEGER ::= 65535
maxnoofCellinTAI INTEGER ::= 65535
maxnoofCellsingNB INTEGER ::= 16384
maxnoofCellsinngeNB INTEGER ::= 256
maxnoofCellsinUEHistoryInfo INTEGER ::= 16
maxnoofCellsUEMovingTrajectory INTEGER ::= 16
maxnoofDRBs INTEGER ::= 32
maxnoofEmergencyAreaID INTEGER ::= 65535
maxnoofEAIforRestart INTEGER ::= 256
maxnoofEPLMNs INTEGER ::= 15
maxnoofEPLMNsPlusOne INTEGER ::= 16
maxnoofE-RABs INTEGER ::= 256
maxnoofErrors INTEGER ::= 256
maxnoofForbTACs INTEGER ::= 4096
maxnoofMultiConnectivity INTEGER ::= 4
maxnoofMultiConnectivityMinusOne INTEGER ::= 3
maxnoofNGConnectionsToReset INTEGER ::= 65536
maxnoofPDUSessions INTEGER ::= 256
maxnoofPLMNs INTEGER ::= 12
maxnoofQosFlows INTEGER ::= 64
maxnoofRANNodeinAoI INTEGER ::= 64
maxnoofRecommendedCells INTEGER ::= 16
maxnoofRecommendedRANNodes INTEGER ::= 16
maxnoofAoI INTEGER ::= 64
maxnoofServedGUAMIs INTEGER ::= 256
maxnoofSliceItems INTEGER ::= 1024
maxnoofTACs INTEGER ::= 256
maxnoofTAIforInactive INTEGER ::= 16
maxnoofTAIforPaging INTEGER ::= 16
maxnoofTAIforRestart INTEGER ::= 2048
maxnoofTAIforWarning INTEGER ::= 65535
maxnoofTAIinAoI INTEGER ::= 16
maxnoofTimePeriods INTEGER ::= 2
maxnoofTNLAssociations INTEGER ::= 32
maxnoofXnExtTLAs INTEGER ::= 16
maxnoofXnGTP-TLAs INTEGER ::= 16
maxnoofXnTLAs INTEGER ::= 2
-- **************************************************************
--
-- IEs
--
-- **************************************************************
id-AllowedNSSAI ProtocolIE-ID ::= 0
id-AMFName ProtocolIE-ID ::= 1
id-AMFOverloadResponse ProtocolIE-ID ::= 2
id-AMFSetID ProtocolIE-ID ::= 3
id-AMF-TNLAssociationFailedToSetupList ProtocolIE-ID ::= 4
id-AMF-TNLAssociationSetupList ProtocolIE-ID ::= 5
id-AMF-TNLAssociationToAddList ProtocolIE-ID ::= 6
id-AMF-TNLAssociationToRemoveList ProtocolIE-ID ::= 7
id-AMF-TNLAssociationToUpdateList ProtocolIE-ID ::= 8
id-AMFTrafficLoadReductionIndication ProtocolIE-ID ::= 9
id-AMF-UE-NGAP-ID ProtocolIE-ID ::= 10
id-AssistanceDataForPaging ProtocolIE-ID ::= 11
id-BroadcastCancelledAreaList ProtocolIE-ID ::= 12
id-BroadcastCompletedAreaList ProtocolIE-ID ::= 13
id-CancelAllWarningMessages ProtocolIE-ID ::= 14
id-Cause ProtocolIE-ID ::= 15
id-CellIDListForRestart ProtocolIE-ID ::= 16
id-ConcurrentWarningMessageInd ProtocolIE-ID ::= 17
id-CoreNetworkAssistanceInformationForInactive ProtocolIE-ID ::= 18
id-CriticalityDiagnostics ProtocolIE-ID ::= 19
id-DataCodingScheme ProtocolIE-ID ::= 20
id-DefaultPagingDRX ProtocolIE-ID ::= 21
id-DirectForwardingPathAvailability ProtocolIE-ID ::= 22
id-EmergencyAreaIDListForRestart ProtocolIE-ID ::= 23
id-EmergencyFallbackIndicator ProtocolIE-ID ::= 24
id-EUTRA-CGI ProtocolIE-ID ::= 25
id-FiveG-S-TMSI ProtocolIE-ID ::= 26
id-GlobalRANNodeID ProtocolIE-ID ::= 27
id-GUAMI ProtocolIE-ID ::= 28
id-HandoverType ProtocolIE-ID ::= 29
id-IMSVoiceSupportIndicator ProtocolIE-ID ::= 30
id-IndexToRFSP ProtocolIE-ID ::= 31
id-InfoOnRecommendedCellsAndRANNodesForPaging ProtocolIE-ID ::= 32
id-LocationReportingRequestType ProtocolIE-ID ::= 33
id-MaskedIMEISV ProtocolIE-ID ::= 34
id-MessageIdentifier ProtocolIE-ID ::= 35
id-MobilityRestrictionList ProtocolIE-ID ::= 36
id-NASC ProtocolIE-ID ::= 37
id-NAS-PDU ProtocolIE-ID ::= 38
id-NASSecurityParametersFromNGRAN ProtocolIE-ID ::= 39
id-NewAMF-UE-NGAP-ID ProtocolIE-ID ::= 40
id-NewSecurityContextInd ProtocolIE-ID ::= 41
id-NGAP-Message ProtocolIE-ID ::= 42
id-NGRAN-CGI ProtocolIE-ID ::= 43
id-NGRANTraceID ProtocolIE-ID ::= 44
id-NR-CGI ProtocolIE-ID ::= 45
id-NRPPa-PDU ProtocolIE-ID ::= 46
id-NumberOfBroadcastsRequested ProtocolIE-ID ::= 47
id-OldAMF ProtocolIE-ID ::= 48
id-OverloadStartNSSAIList ProtocolIE-ID ::= 49
id-PagingDRX ProtocolIE-ID ::= 50
id-PagingOrigin ProtocolIE-ID ::= 51
id-PagingPriority ProtocolIE-ID ::= 52
id-PDUSessionResourceAdmittedList ProtocolIE-ID ::= 53
id-PDUSessionResourceFailedToModifyListModRes ProtocolIE-ID ::= 54
id-PDUSessionResourceFailedToSetupListCxtRes ProtocolIE-ID ::= 55
id-PDUSessionResourceFailedToSetupListHOAck ProtocolIE-ID ::= 56
id-PDUSessionResourceFailedToSetupListPSReq ProtocolIE-ID ::= 57
id-PDUSessionResourceFailedToSetupListSURes ProtocolIE-ID ::= 58
id-PDUSessionResourceHandoverList ProtocolIE-ID ::= 59
id-PDUSessionResourceListCxtRelCpl ProtocolIE-ID ::= 60
id-PDUSessionResourceListHORqd ProtocolIE-ID ::= 61
id-PDUSessionResourceModifyListModCfm ProtocolIE-ID ::= 62
id-PDUSessionResourceModifyListModInd ProtocolIE-ID ::= 63
id-PDUSessionResourceModifyListModReq ProtocolIE-ID ::= 64
id-PDUSessionResourceModifyListModRes ProtocolIE-ID ::= 65
id-PDUSessionResourceNotifyList ProtocolIE-ID ::= 66
id-PDUSessionResourceReleasedListNot ProtocolIE-ID ::= 67
id-PDUSessionResourceReleasedListPSAck ProtocolIE-ID ::= 68
id-PDUSessionResourceReleasedListPSFail ProtocolIE-ID ::= 69
id-PDUSessionResourceReleasedListRelRes ProtocolIE-ID ::= 70
id-PDUSessionResourceSetupListCxtReq ProtocolIE-ID ::= 71
id-PDUSessionResourceSetupListCxtRes ProtocolIE-ID ::= 72
id-PDUSessionResourceSetupListHOReq ProtocolIE-ID ::= 73
id-PDUSessionResourceSetupListSUReq ProtocolIE-ID ::= 74
id-PDUSessionResourceSetupListSURes ProtocolIE-ID ::= 75
id-PDUSessionResourceToBeSwitchedDLList ProtocolIE-ID ::= 76
id-PDUSessionResourceSwitchedList ProtocolIE-ID ::= 77
id-PDUSessionResourceToReleaseListHOCmd ProtocolIE-ID ::= 78
id-PDUSessionResourceToReleaseListRelCmd ProtocolIE-ID ::= 79
id-PLMNSupportList ProtocolIE-ID ::= 80
id-PWSFailedCellIDList ProtocolIE-ID ::= 81
id-RANNodeName ProtocolIE-ID ::= 82
id-RANPagingPriority ProtocolIE-ID ::= 83
id-RANStatusTransfer-TransparentContainer ProtocolIE-ID ::= 84
id-RAN-UE-NGAP-ID ProtocolIE-ID ::= 85
id-RelativeAMFCapacity ProtocolIE-ID ::= 86
id-RepetitionPeriod ProtocolIE-ID ::= 87
id-ResetType ProtocolIE-ID ::= 88
id-RoutingID ProtocolIE-ID ::= 89
id-RRCEstablishmentCause ProtocolIE-ID ::= 90
id-RRCInactiveTransitionReportRequest ProtocolIE-ID ::= 91
id-RRCState ProtocolIE-ID ::= 92
id-SecurityContext ProtocolIE-ID ::= 93
id-SecurityKey ProtocolIE-ID ::= 94
id-SerialNumber ProtocolIE-ID ::= 95
id-ServedGUAMIList ProtocolIE-ID ::= 96
id-SliceSupportList ProtocolIE-ID ::= 97
id-SONConfigurationTransferDL ProtocolIE-ID ::= 98
id-SONConfigurationTransferUL ProtocolIE-ID ::= 99
id-SourceAMF-UE-NGAP-ID ProtocolIE-ID ::= 100
id-SourceToTarget-TransparentContainer ProtocolIE-ID ::= 101
id-SupportedTAList ProtocolIE-ID ::= 102
id-TAIListForPaging ProtocolIE-ID ::= 103
id-TAIListForRestart ProtocolIE-ID ::= 104
id-TargetID ProtocolIE-ID ::= 105
id-TargetToSource-TransparentContainer ProtocolIE-ID ::= 106
id-TimeToWait ProtocolIE-ID ::= 107
id-TraceActivation ProtocolIE-ID ::= 108
id-TraceCollectionEntityIPAddress ProtocolIE-ID ::= 109
id-UEAggregateMaximumBitRate ProtocolIE-ID ::= 110
id-UE-associatedLogicalNG-connectionList ProtocolIE-ID ::= 111
id-UEContextRequest ProtocolIE-ID ::= 112
id-UE-NGAP-IDs ProtocolIE-ID ::= 114
id-UEPagingIdentity ProtocolIE-ID ::= 115
id-UEPresenceInAreaOfInterestList ProtocolIE-ID ::= 116
id-UERadioCapability ProtocolIE-ID ::= 117
id-UERadioCapabilityForPaging ProtocolIE-ID ::= 118
id-UESecurityCapabilities ProtocolIE-ID ::= 119
id-UnavailableGUAMIList ProtocolIE-ID ::= 120
id-UserLocationInformation ProtocolIE-ID ::= 121
id-WarningAreaList ProtocolIE-ID ::= 122
id-WarningMessageContents ProtocolIE-ID ::= 123
id-WarningSecurityInfo ProtocolIE-ID ::= 124
id-WarningType ProtocolIE-ID ::= 125
id-AdditionalUL-NGU-UP-TNLInformation ProtocolIE-ID ::= 126
id-DataForwardingNotPossible ProtocolIE-ID ::= 127
id-DL-NGU-UP-TNLInformation ProtocolIE-ID ::= 128
id-NetworkInstance ProtocolIE-ID ::= 129
id-PDUSessionAggregateMaximumBitRate ProtocolIE-ID ::= 130
id-PDUSessionResourceFailedToModifyListModCfm ProtocolIE-ID ::= 131
id-PDUSessionResourceFailedToSetupListCxtFail ProtocolIE-ID ::= 132
id-PDUSessionResourceListCxtRelReq ProtocolIE-ID ::= 133
id-PDUSessionType ProtocolIE-ID ::= 134
id-QosFlowAddOrModifyRequestList ProtocolIE-ID ::= 135
id-QosFlowSetupRequestList ProtocolIE-ID ::= 136
id-QosFlowToReleaseList ProtocolIE-ID ::= 137
id-SecurityIndication ProtocolIE-ID ::= 138
id-UL-NGU-UP-TNLInformation ProtocolIE-ID ::= 139
id-UL-NGU-UP-TNLModifyList ProtocolIE-ID ::= 140
id-WarningAreaCoordinates ProtocolIE-ID ::= 141
id-PDUSessionResourceSecondaryRATUsageList ProtocolIE-ID ::= 142
id-HandoverFlag ProtocolIE-ID ::= 143
id-SecondaryRATUsageInformation ProtocolIE-ID ::= 144
id-PDUSessionResourceReleaseResponseTransfer ProtocolIE-ID ::= 145
id-RedirectionVoiceFallback ProtocolIE-ID ::= 146
id-UERetentionInformation ProtocolIE-ID ::= 147
id-S-NSSAI ProtocolIE-ID ::= 148
id-PSCellInformation ProtocolIE-ID ::= 149
id-LastEUTRAN-PLMNIdentity ProtocolIE-ID ::= 150
id-MaximumIntegrityProtectedDataRate-DL ProtocolIE-ID ::= 151
id-AdditionalDLForwardingUPTNLInformation ProtocolIE-ID ::= 152
id-AdditionalDLUPTNLInformationForHOList ProtocolIE-ID ::= 153
id-AdditionalNGU-UP-TNLInformation ProtocolIE-ID ::= 154
id-AdditionalDLQosFlowPerTNLInformation ProtocolIE-ID ::= 155
id-SecurityResult ProtocolIE-ID ::= 156
id-ENDC-SONConfigurationTransferDL ProtocolIE-ID ::= 157
id-ENDC-SONConfigurationTransferUL ProtocolIE-ID ::= 158
id-OldAssociatedQosFlowList-ULendmarkerexpected ProtocolIE-ID ::= 159
id-CNTypeRestrictionsForEquivalent ProtocolIE-ID ::= 160
id-CNTypeRestrictionsForServing ProtocolIE-ID ::= 161
id-NewGUAMI ProtocolIE-ID ::= 162
id-ULForwarding ProtocolIE-ID ::= 163
id-ULForwardingUP-TNLInformation ProtocolIE-ID ::= 164
id-CNAssistedRANTuning ProtocolIE-ID ::= 165
id-CommonNetworkInstance ProtocolIE-ID ::= 166
id-NGRAN-TNLAssociationToRemoveList ProtocolIE-ID ::= 167
id-TNLAssociationTransportLayerAddressNGRAN ProtocolIE-ID ::= 168
id-EndpointIPAddressAndPort ProtocolIE-ID ::= 169
id-LocationReportingAdditionalInfo ProtocolIE-ID ::= 170
id-SourceToTarget-AMFInformationReroute ProtocolIE-ID ::= 171
id-AdditionalULForwardingUPTNLInformation ProtocolIE-ID ::= 172
id-SCTP-TLAs ProtocolIE-ID ::= 173
id-SelectedPLMNIdentity ProtocolIE-ID ::= 174
END

-- **************************************************************
--
-- Container definitions
--
-- **************************************************************
NGAP-Containers {
itu-t (0) identified-organization (4) etsi (0) mobileDomain (0)
ngran-Access (22) modules (3) ngap (1) version1 (1) ngap-Containers (5) }
DEFINITIONS AUTOMATIC TAGS ::=
BEGIN
-- **************************************************************
--
-- IE parameter types from other modules.
--
-- **************************************************************
IMPORTS
Criticality,
Presence,
PrivateIE-ID,
ProtocolExtensionID,
ProtocolIE-ID
FROM NGAP-CommonDataTypes
maxPrivateIEs,
maxProtocolExtensions,
maxProtocolIEs
FROM NGAP-Constants;
-- **************************************************************
--
-- Class Definition for Protocol IEs
--
-- **************************************************************
NGAP-PROTOCOL-IES ::= CLASS {
&id ProtocolIE-ID UNIQUE,
&criticality Criticality,
&Value,
&presence Presence
}
WITH SYNTAX {
ID &id
CRITICALITY &criticality
TYPE &Value
PRESENCE &presence
}
-- **************************************************************
--
-- Class Definition for Protocol IEs
--
-- **************************************************************
NGAP-PROTOCOL-IES-PAIR ::= CLASS {
&id ProtocolIE-ID UNIQUE,
&firstCriticality Criticality,
&FirstValue,
&secondCriticality Criticality,
&SecondValue,
&presence Presence
}
WITH SYNTAX {
ID &id
FIRST CRITICALITY &firstCriticality
FIRST TYPE &FirstValue
SECOND CRITICALITY &secondCriticality
SECOND TYPE &SecondValue
PRESENCE &presence
}
-- **************************************************************
--
-- Class Definition for Protocol Extensions
--
-- **************************************************************
NGAP-PROTOCOL-EXTENSION ::= CLASS {
&id ProtocolExtensionID UNIQUE,
&criticality Criticality,
&Extension,
&presence Presence
}
WITH SYNTAX {
ID &id
CRITICALITY &criticality
EXTENSION &Extension
PRESENCE &presence
}
-- **************************************************************
--
-- Class Definition for Private IEs
--
-- **************************************************************
NGAP-PRIVATE-IES ::= CLASS {
&id PrivateIE-ID,
&criticality Criticality,
&Value,
&presence Presence
}
WITH SYNTAX {
ID &id
CRITICALITY &criticality
TYPE &Value
PRESENCE &presence
}
-- **************************************************************
--
-- Container for Protocol IEs
--
-- **************************************************************
ProtocolIE-Container {NGAP-PROTOCOL-IES : IEsSetParam} ::=
SEQUENCE (SIZE (0..maxProtocolIEs)) OF
ProtocolIE-Field {{IEsSetParam}}
ProtocolIE-SingleContainer {NGAP-PROTOCOL-IES : IEsSetParam} ::=
ProtocolIE-Field {{IEsSetParam}}
ProtocolIE-Field {NGAP-PROTOCOL-IES : IEsSetParam} ::= SEQUENCE {
id NGAP-PROTOCOL-IES.&id ({IEsSetParam}),
criticality NGAP-PROTOCOL-IES.&criticality ({IEsSetParam}{@id}),
value NGAP-PROTOCOL-IES.&Value ({IEsSetParam}{@id})
}
-- **************************************************************
--
-- Container for Protocol IE Pairs
--
-- **************************************************************
ProtocolIE-ContainerPair {NGAP-PROTOCOL-IES-PAIR : IEsSetParam} ::=
SEQUENCE (SIZE (0..maxProtocolIEs)) OF
ProtocolIE-FieldPair {{IEsSetParam}}
ProtocolIE-FieldPair {NGAP-PROTOCOL-IES-PAIR : IEsSetParam} ::= SEQUENCE {
id NGAP-PROTOCOL-IES-PAIR.&id ({IEsSetParam}),
firstCriticality NGAP-PROTOCOL-IES-PAIR.&firstCriticality ({IEsSetParam}{@id}),
firstValue NGAP-PROTOCOL-IES-PAIR.&FirstValue ({IEsSetParam}{@id}),
secondCriticality NGAP-PROTOCOL-IES-PAIR.&secondCriticality ({IEsSetParam}{@id}),
secondValue NGAP-PROTOCOL-IES-PAIR.&SecondValue ({IEsSetParam}{@id})
}
-- **************************************************************
--
-- Container Lists for Protocol IE Containers
--
-- **************************************************************
ProtocolIE-ContainerList {INTEGER : lowerBound, INTEGER : upperBound, NGAP-PROTOCOL-IES : IEsSetParam} ::=
SEQUENCE (SIZE (lowerBound..upperBound)) OF
ProtocolIE-SingleContainer {{IEsSetParam}}
ProtocolIE-ContainerPairList {INTEGER : lowerBound, INTEGER : upperBound, NGAP-PROTOCOL-IES-PAIR : IEsSetParam} ::=
SEQUENCE (SIZE (lowerBound..upperBound)) OF
ProtocolIE-ContainerPair {{IEsSetParam}}
-- **************************************************************
--
-- Container for Protocol Extensions
--
-- **************************************************************
ProtocolExtensionContainer {NGAP-PROTOCOL-EXTENSION : ExtensionSetParam} ::=
SEQUENCE (SIZE (1..maxProtocolExtensions)) OF
ProtocolExtensionField {{ExtensionSetParam}}
ProtocolExtensionField {NGAP-PROTOCOL-EXTENSION : ExtensionSetParam} ::= SEQUENCE {
id NGAP-PROTOCOL-EXTENSION.&id ({ExtensionSetParam}),
criticality NGAP-PROTOCOL-EXTENSION.&criticality ({ExtensionSetParam}{@id}),
extensionValue NGAP-PROTOCOL-EXTENSION.&Extension ({ExtensionSetParam}{@id})
}
-- **************************************************************
--
-- Container for Private IEs
--
-- **************************************************************
PrivateIE-Container {NGAP-PRIVATE-IES : IEsSetParam } ::=
SEQUENCE (SIZE (1..maxPrivateIEs)) OF
PrivateIE-Field {{IEsSetParam}}
PrivateIE-Field {NGAP-PRIVATE-IES : IEsSetParam} ::= SEQUENCE {
id NGAP-PRIVATE-IES.&id ({IEsSetParam}),
criticality NGAP-PRIVATE-IES.&criticality ({IEsSetParam}{@id}),
value NGAP-PRIVATE-IES.&Value ({IEsSetParam}{@id})
}
END
