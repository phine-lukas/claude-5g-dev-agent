-- ASN.1 extracted from TS 38.413, all -- ASN1START / -- ASN1STOP blocks,
-- in document order. Generated by scripts/ensure_specs.py; do not edit.

-- **************************************************************
--
-- Elementary Procedure definitions
--
-- **************************************************************
NGAP-PDU-Descriptions {
itu-t (0) identified-organization (4) etsi (0) mobileDomain (0)
ngran-Access (22) modules (3) ngap (1) version1 (1) ngap-PDU-Descriptions (0)}
DEFINITIONS AUTOMATIC TAGS ::=
BEGIN
-- **************************************************************
--
-- IE parameter types from other modules.
--
-- **************************************************************
IMPORTS
Criticality,
ProcedureCode
FROM NGAP-CommonDataTypes
AMFConfigurationUpdate,
AMFConfigurationUpdateAcknowledge,
AMFConfigurationUpdateFailure,
AMFCPRelocationIndication,
AMFStatusIndication,
BroadcastSessionModificationFailure,
BroadcastSessionModificationRequest,
BroadcastSessionModificationResponse,
BroadcastSessionReleaseRequest,
BroadcastSessionReleaseRequired,
BroadcastSessionReleaseResponse,
BroadcastSessionSetupFailure,
BroadcastSessionSetupRequest,
BroadcastSessionSetupResponse,
BroadcastSessionTransportFailure,
BroadcastSessionTransportRequest,
BroadcastSessionTransportResponse,
CellTrafficTrace,
ConnectionEstablishmentIndication,
DeactivateTrace,
DistributionReleaseRequest,
DistributionReleaseResponse,
DistributionSetupFailure,
DistributionSetupRequest,
DistributionSetupResponse,
DownlinkNASTransport,
DownlinkNonUEAssociatedNRPPaTransport,
DownlinkRANConfigurationTransfer,
DownlinkRANEarlyStatusTransfer,
DownlinkRANStatusTransfer,
DownlinkUEAssociatedNRPPaTransport,
ErrorIndication,
HandoverCancel,
HandoverCancelAcknowledge,
HandoverCommand,
HandoverFailure,
HandoverNotify,
HandoverPreparationFailure,
HandoverRequest,
HandoverRequestAcknowledge,
HandoverRequired,
HandoverSuccess,
InitialContextSetupFailure,
InitialContextSetupRequest,
InitialContextSetupResponse,
InitialUEMessage,
LocationReport,
LocationReportingControl,
LocationReportingFailureIndication,
MTCommunicationHandlingRequest,
MTCommunicationHandlingResponse,
MTCommunicationHandlingFailure,
MulticastSessionActivationFailure,
MulticastSessionActivationRequest,
MulticastSessionActivationResponse,
MulticastSessionDeactivationRequest,
MulticastSessionDeactivationResponse,
MulticastSessionUpdateFailure,
MulticastSessionUpdateRequest,
MulticastSessionUpdateResponse,
MulticastGroupPaging,
NASNonDeliveryIndication,
NGReset,
NGResetAcknowledge,
NGSetupFailure,
NGSetupRequest,
NGSetupResponse,
OverloadStart,
OverloadStop,
Paging,
PathSwitchRequest,
PathSwitchRequestAcknowledge,
PathSwitchRequestFailure,
PDUSessionResourceModifyConfirm,
PDUSessionResourceModifyIndication,
PDUSessionResourceModifyRequest,
PDUSessionResourceModifyResponse,
PDUSessionResourceNotify,
PDUSessionResourceReleaseCommand,
PDUSessionResourceReleaseResponse,
PDUSessionResourceSetupRequest,
PDUSessionResourceSetupResponse,
PrivateMessage,
PWSCancelRequest,
PWSCancelResponse,
PWSFailureIndication,
PWSRestartIndication,
RANConfigurationUpdate,
RANConfigurationUpdateAcknowledge,
RANConfigurationUpdateFailure,
RANCPRelocationIndication,
RANPagingRequest,
RerouteNASRequest,
RetrieveUEInformation,
RRCInactiveTransitionReport,
SecondaryRATDataUsageReport,
TimingSynchronisationStatusRequest,
TimingSynchronisationStatusResponse,
TimingSynchronisationStatusFailure,
TimingSynchronisationStatusReport,
TraceFailureIndication,
TraceStart,
UEContextModificationFailure,
UEContextModificationRequest,
UEContextModificationResponse,
UEContextReleaseCommand,
UEContextReleaseComplete,
UEContextReleaseRequest,
UEContextResumeRequest,
UEContextResumeResponse,
UEContextResumeFailure,
UEContextSuspendRequest,
UEContextSuspendResponse,
UEContextSuspendFailure,
UEInformationTransfer,
UERadioCapabilityCheckRequest,
UERadioCapabilityCheckResponse,
UERadioCapabilityIDMappingRequest,
UERadioCapabilityIDMappingResponse,
UERadioCapabilityInfoIndication,
UETNLABindingReleaseRequest,
UplinkNASTransport,
UplinkNonUEAssociatedNRPPaTransport,
UplinkRANConfigurationTransfer,
UplinkRANEarlyStatusTransfer,
UplinkRANStatusTransfer,
UplinkUEAssociatedNRPPaTransport,
WriteReplaceWarningRequest,
WriteReplaceWarningResponse,
UplinkRIMInformationTransfer,
DownlinkRIMInformationTransfer
FROM NGAP-PDU-Contents
id-AMFConfigurationUpdate,
id-AMFCPRelocationIndication,
id-AMFStatusIndication,
id-BroadcastSessionModification,
id-BroadcastSessionRelease,
id-BroadcastSessionReleaseRequired,
id-BroadcastSessionSetup,
id-BroadcastSessionTransport,
id-CellTrafficTrace,
id-ConnectionEstablishmentIndication,
id-DeactivateTrace,
id-DistributionRelease,
id-DistributionSetup,
id-DownlinkNASTransport,
id-DownlinkNonUEAssociatedNRPPaTransport,
id-DownlinkRANConfigurationTransfer,
id-DownlinkRANEarlyStatusTransfer,
id-DownlinkRANStatusTransfer,
id-DownlinkRIMInformationTransfer,
id-DownlinkUEAssociatedNRPPaTransport,
id-ErrorIndication,
id-HandoverCancel,
id-HandoverNotification,
id-HandoverPreparation,
id-HandoverResourceAllocation,
id-HandoverSuccess,
id-InitialContextSetup,
id-InitialUEMessage,
id-LocationReport,
id-LocationReportingControl,
id-LocationReportingFailureIndication,
id-MTCommunicationHandling,
id-MulticastGroupPaging,
id-MulticastSessionActivation,
id-MulticastSessionDeactivation,
id-MulticastSessionUpdate,
id-NASNonDeliveryIndication,
id-NGReset,
id-NGSetup,
id-OverloadStart,
id-OverloadStop,
id-Paging,
id-PathSwitchRequest,
id-PDUSessionResourceModify,
id-PDUSessionResourceModifyIndication,
id-PDUSessionResourceNotify,
id-PDUSessionResourceRelease,
id-PDUSessionResourceSetup,
id-PrivateMessage,
id-PWSCancel,
id-PWSFailureIndication,
id-PWSRestartIndication,
id-RANConfigurationUpdate,
id-RANCPRelocationIndication,
id-RANPagingRequest,
id-RerouteNASRequest,
id-RetrieveUEInformation,
id-RRCInactiveTransitionReport,
id-SecondaryRATDataUsageReport,
id-TimingSynchronisationStatus,
id-TimingSynchronisationStatusReport,
id-TraceFailureIndication,
id-TraceStart,
id-UEContextModification,
id-UEContextRelease,
id-UEContextReleaseRequest,
id-UEContextResume,
id-UEContextSuspend,
id-UEInformationTransfer,
id-UERadioCapabilityCheck,
id-UERadioCapabilityIDMapping,
id-UERadioCapabilityInfoIndication,
id-UETNLABindingRelease,
id-UplinkNASTransport,
id-UplinkNonUEAssociatedNRPPaTransport,
id-UplinkRANConfigurationTransfer,
id-UplinkRANEarlyStatusTransfer,
id-UplinkRANStatusTransfer,
id-UplinkRIMInformationTransfer,
id-UplinkUEAssociatedNRPPaTransport,
id-WriteReplaceWarning
FROM NGAP-Constants;
-- **************************************************************
--
-- Interface Elementary Procedure Class
--
-- **************************************************************
NGAP-ELEMENTARY-PROCEDURE ::= CLASS {
&InitiatingMessage ,
&SuccessfulOutcome OPTIONAL,
&UnsuccessfulOutcome OPTIONAL,
&procedureCode ProcedureCode UNIQUE,
&criticality Criticality DEFAULT ignore
}
WITH SYNTAX {
INITIATING MESSAGE &InitiatingMessage
[SUCCESSFUL OUTCOME &SuccessfulOutcome]
[UNSUCCESSFUL OUTCOME &UnsuccessfulOutcome]
PROCEDURE CODE &procedureCode
[CRITICALITY &criticality]
}
-- **************************************************************
--
-- Interface PDU Definition
--
-- **************************************************************
NGAP-PDU ::= CHOICE {
initiatingMessage InitiatingMessage,
successfulOutcome SuccessfulOutcome,
unsuccessfulOutcome UnsuccessfulOutcome,
...
}
InitiatingMessage ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&InitiatingMessage ({NGAP-ELEMENTARY-PROCEDURES}{@procedureCode})
}
SuccessfulOutcome ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&SuccessfulOutcome ({NGAP-ELEMENTARY-PROCEDURES}{@procedureCode})
}
UnsuccessfulOutcome ::= SEQUENCE {
procedureCode NGAP-ELEMENTARY-PROCEDURE.&procedureCode ({NGAP-ELEMENTARY-PROCEDURES}),
criticality NGAP-ELEMENTARY-PROCEDURE.&criticality ({NGAP-ELEMENTARY-PROCEDURES}{@procedureCode}),
value NGAP-ELEMENTARY-PROCEDURE.&UnsuccessfulOutcome ({NGAP-ELEMENTARY-PROCEDURES}{@procedureCode})
}
-- **************************************************************
--
-- Interface Elementary Procedure List
--
-- **************************************************************
NGAP-ELEMENTARY-PROCEDURES NGAP-ELEMENTARY-PROCEDURE ::= {
NGAP-ELEMENTARY-PROCEDURES-CLASS-1 |
NGAP-ELEMENTARY-PROCEDURES-CLASS-2,
...
}
NGAP-ELEMENTARY-PROCEDURES-CLASS-1 NGAP-ELEMENTARY-PROCEDURE ::= {
aMFConfigurationUpdate |
broadcastSessionModification |
broadcastSessionRelease |
broadcastSessionSetup |
broadcastSessionTransport |
distributionSetup |
distributionRelease |
handoverCancel |
handoverPreparation |
handoverResourceAllocation |
initialContextSetup |
mTCommunicationHandling |
multicastSessionActivation |
multicastSessionDeactivation |
multicastSessionUpdate |
nGReset |
nGSetup |
pathSwitchRequest |
pDUSessionResourceModify |
pDUSessionResourceModifyIndication |
pDUSessionResourceRelease |
pDUSessionResourceSetup |
pWSCancel |
rANConfigurationUpdate |
timingSynchronisationStatus |
uEContextModification |
uEContextRelease |
uEContextResume |
uEContextSuspend |
uERadioCapabilityCheck |
uERadioCapabilityIDMapping |
writeReplaceWarning ,
...
}
NGAP-ELEMENTARY-PROCEDURES-CLASS-2 NGAP-ELEMENTARY-PROCEDURE ::= {
aMFCPRelocationIndication |
aMFStatusIndication |
broadcastSessionReleaseRequired |
cellTrafficTrace |
connectionEstablishmentIndication |
deactivateTrace |
downlinkNASTransport |
downlinkNonUEAssociatedNRPPaTransport |
downlinkRANConfigurationTransfer |
downlinkRANEarlyStatusTransfer |
downlinkRANStatusTransfer |
downlinkRIMInformationTransfer |
downlinkUEAssociatedNRPPaTransport |
errorIndication |
handoverNotification |
handoverSuccess |
initialUEMessage |
locationReport |
locationReportingControl |
locationReportingFailureIndication |
multicastGroupPaging |
nASNonDeliveryIndication |
overloadStart |
overloadStop |
paging |
pDUSessionResourceNotify |
privateMessage |
pWSFailureIndication |
pWSRestartIndication |
rANCPRelocationIndication |
rANPagingRequest |
rerouteNASRequest |
retrieveUEInformation |
rRCInactiveTransitionReport |
secondaryRATDataUsageReport |
timingSynchronisationStatusReport |
traceFailureIndication |
traceStart |
uEContextReleaseRequest |
uEInformationTransfer |
uERadioCapabilityInfoIndication |
uETNLABindingRelease |
uplinkNASTransport |
uplinkNonUEAssociatedNRPPaTransport |
uplinkRANConfigurationTransfer |
uplinkRANEarlyStatusTransfer |
uplinkRANStatusTransfer |
uplinkRIMInformationTransfer |
uplinkUEAssociatedNRPPaTransport ,
...
}
-- **************************************************************
--
-- Interface Elementary Procedures
--
-- **************************************************************
aMFConfigurationUpdate NGAP-ELEMENTARY-PROCEDURE ::= {
INITIATING MESSAGE AMFConfigurationUpdate
SUCCESSFUL OUTCOME AMFConfigurationUpdateAcknowledge
UNSUCCESSFUL OUTCOME AMFConfigurationUpdateFailure
PROCEDURE CODE id-AMFConfigurationUpdate
CRITICALITY reject
}
aMFCPRelocationIndication NGAP-ELEMENTARY-PROCEDURE ::= {
INITIATING MESSAGE AMFCPRelocationIndication
PROCEDURE CODE id-AMFCPRelocationIndication
CRITICALITY reject
}
aMFStatusIndication NGAP-ELEMENTARY-PROCEDURE ::={
INITIATING MESSAGE AMFStatusIndication
PROCEDURE CODE id-AMFStatusIndication
CRITICALITY ignore
}
broadcastSessionModification NGAP-ELEMENTARY-PROCEDURE ::= {
INITIATING MESSAGE BroadcastSessionModificationRequest
SUCCESSFUL OUTCOME BroadcastSessionModificationResponse
UNSUCCESSFUL OUTCOME BroadcastSessionModificationFailure
PROCEDURE CODE id-BroadcastSessionModification
CRITICALITY reject
}
broadcastSessionRelease NGAP-ELEMENTARY-PROCEDURE ::= {
INITIATING MESSAGE BroadcastSessionReleaseRequest
SUCCESSFUL OUTCOME BroadcastSessionReleaseResponse
PROCEDURE CODE id-BroadcastSessionRelease
CRITICALITY reject
}
broadcastSessionReleaseRequired NGAP-ELEMENTARY-PROCEDURE ::= {
INITIATING MESSAGE BroadcastSessionReleaseRequired
PROCEDURE CODE id-BroadcastSessionReleaseRequired
CRITICALITY reject
}
broadcastSessionSetup NGAP-ELEMENTARY-PROCEDURE ::= {
INITIATING MESSAGE BroadcastSessionSetupRequest
SUCCESSFUL OUTCOME BroadcastSessionSetupResponse
UNSUCCESSFUL OUTCOME BroadcastSessionSetupFailure
PROCEDURE CODE id-BroadcastSessionSetup
CRITICALITY reject
}
broadcastSessionTransport NGAP-ELEMENTARY-PROCEDURE ::= {
INITIATING MESSAGE BroadcastSessionTransportRequest
SUCCESSFUL OUTCOME BroadcastSessionTransportResponse
UNSUCCESSFUL OUTCOME BroadcastSessionTransportFailure
PROCEDURE CODE id-BroadcastSessionTransport
CRITICALITY reject
}
cellTrafficTrace NGAP-ELEMENTARY-PROCEDURE ::={
INITIATING MESSAGE CellTrafficTrace
PROCEDURE CODE id-CellTrafficTrace
CRITICALITY ignore
}
connectionEstablishmentIndication NGAP-ELEMENTARY-PROCEDURE ::= {
INITIATING MESSAGE ConnectionEstablishmentIndication
PROCEDURE CODE id-ConnectionEstablishmentIndication
CRITICALITY reject
}
deactivateTrace NGAP-ELEMENTARY-PROCEDURE ::= {
INITIATING MESSAGE DeactivateTrace
PROCEDURE CODE id-DeactivateTrace
CRITICALITY ignore
}
distributionSetup NGAP-ELEMENTARY-PROCEDURE ::= {
INITIATING MESSAGE DistributionSetupRequest
SUCCESSFUL OUTCOME DistributionSetupResponse
UNSUCCESSFUL OUTCOME DistributionSetupFailure
PROCEDURE CODE id-DistributionSetup
CRITICALITY reject
}
distributionRelease NGAP-ELEMENTARY-PROCEDURE ::= {
INITIATING MESSAGE DistributionReleaseRequest
SUCCESSFUL OUTCOME DistributionReleaseResponse
PROCEDURE CODE id-DistributionRelease
CRITICALITY reject
}
downlinkNASTransport NGAP-ELEMENTARY-PROCEDURE ::= {
INITIATING MESSAGE DownlinkNASTransport
PROCEDURE CODE id-DownlinkNASTransport
CRITICALITY ignore
}
downlinkNonUEAssociatedNRPPaTransport NGAP-ELEMENTARY-PROCEDURE ::= {
INITIATING MESSAGE DownlinkNonUEAssociatedNRPPaTransport
PROCEDURE CODE id-DownlinkNonUEAssociatedNRPPaTransport
CRITICALITY ignore
}
downlinkRANConfigurationTransfer NGAP-ELEMENTARY-PROCEDURE ::= {
INITIATING MESSAGE DownlinkRANConfigurationTransfer
PROCEDURE CODE id-DownlinkRANConfigurationTransfer
CRITICALITY ignore
}
downlinkRANEarlyStatusTransfer NGAP-ELEMENTARY-PROCEDURE ::= {
INITIATING MESSAGE DownlinkRANEarlyStatusTransfer
PROCEDURE CODE id-DownlinkRANEarlyStatusTransfer
CRITICALITY ignore
}
downlinkRANStatusTransfer NGAP-ELEMENTARY-PROCEDURE ::= {
INITIATING MESSAGE DownlinkRANStatusTransfer
PROCEDURE CODE id-DownlinkRANStatusTransfer
CRITICALITY ignore
}
downlinkUEAssociatedNRPPaTransport NGAP-ELEMENTARY-PROCEDURE ::= {
INITIATING MESSAGE DownlinkUEAssociatedNRPPaTransport
PROCEDURE CODE id-DownlinkUEAssociatedNRPPaTransport
CRITICALITY ignore
}
errorIndication NGAP-ELEMENTARY-PROCEDURE ::= {
INITIATING MESSAGE ErrorIndication
PROCEDURE CODE id-ErrorIndication
CRITICALITY ignore
}
handoverCancel NGAP-ELEMENTARY-PROCEDURE ::= {
INITIATING MESSAGE HandoverCancel
SUCCESSFUL OUTCOME HandoverCancelAcknowledge
PROCEDURE CODE id-HandoverCancel
CRITICALITY reject
}
handoverNotification NGAP-ELEMENTARY-PROCEDURE ::= {
INITIATING MESSAGE HandoverNotify
PROCEDURE CODE id-HandoverNotification
CRITICALITY ignore
}
handoverPreparation NGAP-ELEMENTARY-PROCEDURE ::= {
INITIATING MESSAGE HandoverRequired
SUCCESSFUL OUTCOME HandoverCommand
UNSUCCESSFUL OUTCOME HandoverPreparationFailure
PROCEDURE CODE id-HandoverPreparation
CRITICALITY reject
}
handoverResourceAllocation NGAP-ELEMENTARY-PROCEDURE ::= {
INITIATING MESSAGE HandoverRequest
SUCCESSFUL OUTCOME HandoverRequestAcknowledge
UNSUCCESSFUL OUTCOME HandoverFailure
PROCEDURE CODE id-HandoverResourceAllocation
CRITICALITY reject
}
handoverSuccess NGAP-ELEMENTARY-PROCEDURE ::= {
INITIATING MESSAGE HandoverSuccess
PROCEDURE CODE id-HandoverSuccess
CRITICALITY ignore
}
initialContextSetup NGAP-ELEMENTARY-PROCEDURE ::= {
INITIATING MESSAGE InitialContextSetupRequest
SUCCESSFUL OUTCOME InitialContextSetupResponse
UNSUCCESSFUL OUTCOME InitialContextSetupFailure
PROCEDURE CODE id-InitialContextSetup
CRITICALITY reject
}
initialUEMessage NGAP-ELEMENTARY-PROCEDURE ::= {
INITIATING MESSAGE InitialUEMessage
PROCEDURE CODE id-InitialUEMessage
CRITICALITY ignore
}
locationReport NGAP-ELEMENTARY-PROCEDURE ::= {
INITIATING MESSAGE LocationReport
PROCEDURE CODE id-LocationReport
CRITICALITY ignore
}
locationReportingControl NGAP-ELEMENTARY-PROCEDURE ::= {
INITIATING MESSAGE LocationReportingControl
PROCEDURE CODE id-LocationReportingControl
CRITICALITY ignore
}
locationReportingFailureIndication NGAP-ELEMENTARY-PROCEDURE ::= {
INITIATING MESSAGE LocationReportingFailureIndication
PROCEDURE CODE id-LocationReportingFailureIndication
CRITICALITY ignore
}
mTCommunicationHandling NGAP-ELEMENTARY-PROCEDURE ::= {
INITIATING MESSAGE MTCommunicationHandlingRequest
SUCCESSFUL OUTCOME MTCommunicationHandlingResponse
UNSUCCESSFUL OUTCOME MTCommunicationHandlingFailure
PROCEDURE CODE id-MTCommunicationHandling
CRITICALITY reject
}
multicastSessionActivation NGAP-ELEMENTARY-PROCEDURE ::= {
INITIATING MESSAGE MulticastSessionActivationRequest
SUCCESSFUL OUTCOME MulticastSessionActivationResponse
UNSUCCESSFUL OUTCOME MulticastSessionActivationFailure
PROCEDURE CODE id-MulticastSessionActivation
CRITICALITY reject
}
multicastSessionDeactivation NGAP-ELEMENTARY-PROCEDURE ::= {
INITIATING MESSAGE MulticastSessionDeactivationRequest
SUCCESSFUL OUTCOME MulticastSessionDeactivationResponse
PROCEDURE CODE id-MulticastSessionDeactivation
CRITICALITY reject
}
multicastSessionUpdate NGAP-ELEMENTARY-PROCEDURE ::= {
INITIATING MESSAGE MulticastSessionUpdateRequest
SUCCESSFUL OUTCOME MulticastSessionUpdateResponse
UNSUCCESSFUL OUTCOME MulticastSessionUpdateFailure
PROCEDURE CODE id-MulticastSessionUpdate
CRITICALITY reject
}
multicastGroupPaging NGAP-ELEMENTARY-PROCEDURE ::= {
INITIATING MESSAGE MulticastGroupPaging
PROCEDURE CODE id-MulticastGroupPaging
CRITICALITY ignore
}
nASNonDeliveryIndication NGAP-ELEMENTARY-PROCEDURE ::= {
INITIATING MESSAGE NASNonDeliveryIndication
PROCEDURE CODE id-NASNonDeliveryIndication
CRITICALITY ignore
}
nGReset NGAP-ELEMENTARY-PROCEDURE ::= {
INITIATING MESSAGE NGReset
SUCCESSFUL OUTCOME NGResetAcknowledge
PROCEDURE CODE id-NGReset
CRITICALITY reject
}
nGSetup NGAP-ELEMENTARY-PROCEDURE ::= {
INITIATING MESSAGE NGSetupRequest
SUCCESSFUL OUTCOME NGSetupResponse
UNSUCCESSFUL OUTCOME NGSetupFailure
PROCEDURE CODE id-NGSetup
CRITICALITY reject
}
overloadStart NGAP-ELEMENTARY-PROCEDURE ::= {
INITIATING MESSAGE OverloadStart
PROCEDURE CODE id-OverloadStart
CRITICALITY ignore
}
overloadStop NGAP-ELEMENTARY-PROCEDURE ::= {
INITIATING MESSAGE OverloadStop
PROCEDURE CODE id-OverloadStop
CRITICALITY reject
}
paging NGAP-ELEMENTARY-PROCEDURE ::= {
INITIATING MESSAGE Paging
PROCEDURE CODE id-Paging
CRITICALITY ignore
}
pathSwitchRequest NGAP-ELEMENTARY-PROCEDURE ::= {
INITIATING MESSAGE PathSwitchRequest
SUCCESSFUL OUTCOME PathSwitchRequestAcknowledge
UNSUCCESSFUL OUTCOME PathSwitchRequestFailure
PROCEDURE CODE id-PathSwitchRequest
CRITICALITY reject
}
pDUSessionResourceModify NGAP-ELEMENTARY-PROCEDURE ::= {
INITIATING MESSAGE PDUSessionResourceModifyRequest
SUCCESSFUL OUTCOME PDUSessionResourceModifyResponse
PROCEDURE CODE id-PDUSessionResourceModify
CRITICALITY reject
}
pDUSessionResourceModifyIndication NGAP-ELEMENTARY-PROCEDURE ::= {
INITIATING MESSAGE PDUSessionResourceModifyIndication
SUCCESSFUL OUTCOME PDUSessionResourceModifyConfirm
PROCEDURE CODE id-PDUSessionResourceModifyIndication
CRITICALITY reject
}
pDUSessionResourceNotify NGAP-ELEMENTARY-PROCEDURE ::= {
INITIATING MESSAGE PDUSessionResourceNotify
PROCEDURE CODE id-PDUSessionResourceNotify
CRITICALITY ignore
}
pDUSessionResourceRelease NGAP-ELEMENTARY-PROCEDURE ::= {
INITIATING MESSAGE PDUSessionResourceReleaseCommand
SUCCESSFUL OUTCOME PDUSessionResourceReleaseResponse
PROCEDURE CODE id-PDUSessionResourceRelease
CRITICALITY reject
}
pDUSessionResourceSetup NGAP-ELEMENTARY-PROCEDURE ::= {
INITIATING MESSAGE PDUSessionResourceSetupRequest
SUCCESSFUL OUTCOME PDUSessionResourceSetupResponse
PROCEDURE CODE id-PDUSessionResourceSetup
CRITICALITY reject
}
privateMessage NGAP-ELEMENTARY-PROCEDURE ::= {
INITIATING MESSAGE PrivateMessage
PROCEDURE CODE id-PrivateMessage
CRITICALITY ignore
}
pWSCancel NGAP-ELEMENTARY-PROCEDURE ::= {
INITIATING MESSAGE PWSCancelRequest
SUCCESSFUL OUTCOME PWSCancelResponse
PROCEDURE CODE id-PWSCancel
CRITICALITY reject
}
pWSFailureIndication NGAP-ELEMENTARY-PROCEDURE ::= {
INITIATING MESSAGE PWSFailureIndication
PROCEDURE CODE id-PWSFailureIndication
CRITICALITY ignore
}
pWSRestartIndication NGAP-ELEMENTARY-PROCEDURE ::= {
INITIATING MESSAGE PWSRestartIndication
PROCEDURE CODE id-PWSRestartIndication
CRITICALITY ignore
}
rANConfigurationUpdate NGAP-ELEMENTARY-PROCEDURE ::= {
INITIATING MESSAGE RANConfigurationUpdate
SUCCESSFUL OUTCOME RANConfigurationUpdateAcknowledge
UNSUCCESSFUL OUTCOME RANConfigurationUpdateFailure
PROCEDURE CODE id-RANConfigurationUpdate
CRITICALITY reject
}
rANCPRelocationIndication NGAP-ELEMENTARY-PROCEDURE ::= {
INITIATING MESSAGE RANCPRelocationIndication
PROCEDURE CODE id-RANCPRelocationIndication
CRITICALITY reject
}
rANPagingRequest NGAP-ELEMENTARY-PROCEDURE ::= {
INITIATING MESSAGE RANPagingRequest
PROCEDURE CODE id-RANPagingRequest
CRITICALITY ignore
}
rerouteNASRequest NGAP-ELEMENTARY-PROCEDURE ::= {
INITIATING MESSAGE RerouteNASRequest
PROCEDURE CODE id-RerouteNASRequest
CRITICALITY reject
}
retrieveUEInformation NGAP-ELEMENTARY-PROCEDURE ::= {
INITIATING MESSAGE RetrieveUEInformation
PROCEDURE CODE id-RetrieveUEInformation
CRITICALITY reject
}
rRCInactiveTransitionReport NGAP-ELEMENTARY-PROCEDURE ::= {
INITIATING MESSAGE RRCInactiveTransitionReport
PROCEDURE CODE id-RRCInactiveTransitionReport
CRITICALITY ignore
}
secondaryRATDataUsageReport NGAP-ELEMENTARY-PROCEDURE ::= {
INITIATING MESSAGE SecondaryRATDataUsageReport
PROCEDURE CODE id-SecondaryRATDataUsageReport
CRITICALITY ignore
}
timingSynchronisationStatus NGAP-ELEMENTARY-PROCEDURE ::= {
INITIATING MESSAGE TimingSynchronisationStatusRequest
SUCCESSFUL OUTCOME TimingSynchronisationStatusResponse
UNSUCCESSFUL OUTCOME TimingSynchronisationStatusFailure
PROCEDURE CODE id-TimingSynchronisationStatus
CRITICALITY reject
}
timingSynchronisationStatusReport NGAP-ELEMENTARY-PROCEDURE ::= {
INITIATING MESSAGE TimingSynchronisationStatusReport
PROCEDURE CODE id-TimingSynchronisationStatusReport
CRITICALITY ignore
}
traceFailureIndication NGAP-ELEMENTARY-PROCEDURE ::= {
INITIATING MESSAGE TraceFailureIndication
PROCEDURE CODE id-TraceFailureIndication
CRITICALITY ignore
}
traceStart NGAP-ELEMENTARY-PROCEDURE ::= {
INITIATING MESSAGE TraceStart
PROCEDURE CODE id-TraceStart
CRITICALITY ignore
}
uEContextModification NGAP-ELEMENTARY-PROCEDURE ::= {
INITIATING MESSAGE UEContextModificationRequest
SUCCESSFUL OUTCOME UEContextModificationResponse
UNSUCCESSFUL OUTCOME UEContextModificationFailure
PROCEDURE CODE id-UEContextModification
CRITICALITY reject
}
uEContextRelease NGAP-ELEMENTARY-PROCEDURE ::= {
INITIATING MESSAGE UEContextReleaseCommand
SUCCESSFUL OUTCOME UEContextReleaseComplete
PROCEDURE CODE id-UEContextRelease
CRITICALITY reject
}
uEContextReleaseRequest NGAP-ELEMENTARY-PROCEDURE ::= {
INITIATING MESSAGE UEContextReleaseRequest
PROCEDURE CODE id-UEContextReleaseRequest
CRITICALITY ignore
}
uEContextResume NGAP-ELEMENTARY-PROCEDURE ::= {
INITIATING MESSAGE UEContextResumeRequest
SUCCESSFUL OUTCOME UEContextResumeResponse
UNSUCCESSFUL OUTCOME UEContextResumeFailure
PROCEDURE CODE id-UEContextResume
CRITICALITY reject
}
uEContextSuspend NGAP-ELEMENTARY-PROCEDURE ::= {
INITIATING MESSAGE UEContextSuspendRequest
SUCCESSFUL OUTCOME UEContextSuspendResponse
UNSUCCESSFUL OUTCOME UEContextSuspendFailure
PROCEDURE CODE id-UEContextSuspend
CRITICALITY reject
}
uEInformationTransfer NGAP-ELEMENTARY-PROCEDURE ::= {
INITIATING MESSAGE UEInformationTransfer
PROCEDURE CODE id-UEInformationTransfer
CRITICALITY reject
}
uERadioCapabilityCheck NGAP-ELEMENTARY-PROCEDURE ::= {
INITIATING MESSAGE UERadioCapabilityCheckRequest
SUCCESSFUL OUTCOME UERadioCapabilityCheckResponse
PROCEDURE CODE id-UERadioCapabilityCheck
CRITICALITY reject
}
uERadioCapabilityIDMapping NGAP-ELEMENTARY-PROCEDURE ::= {
INITIATING MESSAGE UERadioCapabilityIDMappingRequest
SUCCESSFUL OUTCOME UERadioCapabilityIDMappingResponse
PROCEDURE CODE id-UERadioCapabilityIDMapping
CRITICALITY reject
}
uERadioCapabilityInfoIndication NGAP-ELEMENTARY-PROCEDURE ::= {
INITIATING MESSAGE UERadioCapabilityInfoIndication
PROCEDURE CODE id-UERadioCapabilityInfoIndication
CRITICALITY ignore
}
uETNLABindingRelease NGAP-ELEMENTARY-PROCEDURE ::= {
INITIATING MESSAGE UETNLABindingReleaseRequest
PROCEDURE CODE id-UETNLABindingRelease
CRITICALITY ignore
}
uplinkNASTransport NGAP-ELEMENTARY-PROCEDURE ::= {
INITIATING MESSAGE UplinkNASTransport
PROCEDURE CODE id-UplinkNASTransport
CRITICALITY ignore
}
uplinkNonUEAssociatedNRPPaTransport NGAP-ELEMENTARY-PROCEDURE ::= {
INITIATING MESSAGE UplinkNonUEAssociatedNRPPaTransport
PROCEDURE CODE id-UplinkNonUEAssociatedNRPPaTransport
CRITICALITY ignore
}
uplinkRANConfigurationTransfer NGAP-ELEMENTARY-PROCEDURE ::= {
INITIATING MESSAGE UplinkRANConfigurationTransfer
PROCEDURE CODE id-UplinkRANConfigurationTransfer
CRITICALITY ignore
}
uplinkRANEarlyStatusTransfer NGAP-ELEMENTARY-PROCEDURE ::= {
INITIATING MESSAGE UplinkRANEarlyStatusTransfer
PROCEDURE CODE id-UplinkRANEarlyStatusTransfer
CRITICALITY reject
}
uplinkRANStatusTransfer NGAP-ELEMENTARY-PROCEDURE ::= {
INITIATING MESSAGE UplinkRANStatusTransfer
PROCEDURE CODE id-UplinkRANStatusTransfer
CRITICALITY ignore
}
uplinkUEAssociatedNRPPaTransport NGAP-ELEMENTARY-PROCEDURE ::= {
INITIATING MESSAGE UplinkUEAssociatedNRPPaTransport
PROCEDURE CODE id-UplinkUEAssociatedNRPPaTransport
CRITICALITY ignore
}
writeReplaceWarning NGAP-ELEMENTARY-PROCEDURE ::= {
INITIATING MESSAGE WriteReplaceWarningRequest
SUCCESSFUL OUTCOME WriteReplaceWarningResponse
PROCEDURE CODE id-WriteReplaceWarning
CRITICALITY reject
}
uplinkRIMInformationTransfer NGAP-ELEMENTARY-PROCEDURE ::= {
INITIATING MESSAGE UplinkRIMInformationTransfer
PROCEDURE CODE id-UplinkRIMInformationTransfer
CRITICALITY ignore
}
downlinkRIMInformationTransfer NGAP-ELEMENTARY-PROCEDURE ::= {
INITIATING MESSAGE DownlinkRIMInformationTransfer
PROCEDURE CODE id-DownlinkRIMInformationTransfer
CRITICALITY ignore
}
END

-- **************************************************************
--
-- PDU definitions for NGAP.
--
-- **************************************************************
NGAP-PDU-Contents {
itu-t (0) identified-organization (4) etsi (0) mobileDomain (0)
ngran-Access (22) modules (3) ngap (1) version1 (1) ngap-PDU-Contents (1) }
DEFINITIONS AUTOMATIC TAGS ::=
BEGIN
-- **************************************************************
--
-- IE parameter types from other modules.
--
-- **************************************************************
IMPORTS
A2X-PC5-QoS-Parameters,
AerialUEsubscriptionInformation,
AllowedNSSAI,
AMFName,
AMFSetID,
AMF-TNLAssociationSetupList,
AMF-TNLAssociationToAddList,
AMF-TNLAssociationToRemoveList,
AMF-TNLAssociationToUpdateList,
AMF-UE-NGAP-ID,
AssistanceDataForPaging,
AssociatedSessionID,
AUN3DeviceAccessInfo,
AuthenticatedIndication,
BroadcastCancelledAreaList,
BroadcastCompletedAreaList,
BroadcastTransportFailureTransfer,
BroadcastTransportRequestTransfer,
BroadcastTransportResponseTransfer,
CancelAllWarningMessages,
Cause,
CellIDListForRestart,
CEmodeBrestricted,
CEmodeBSupport-Indicator,
CNAssistedRANTuning,
ConcurrentWarningMessageInd,
CoreNetworkAssistanceInformationForInactive,
CPTransportLayerInformation,
CriticalityDiagnostics,
DataCodingScheme,
DirectForwardingPathAvailability,
DL-CP-SecurityInformation,
DL-Signalling,
EarlyStatusTransfer-TransparentContainer,
EDT-Session,
EmergencyAreaIDListForRestart,
EmergencyFallbackIndicator,
EN-DCSONConfigurationTransfer,
EndIndication,
Enhanced-CoverageRestriction,
ERedCapIndication,
EUTRA-CGI,
EUTRA-PagingeDRXInformation,
Extended-AMFName,
Extended-ConnectedTime,
Extended-RANNodeName,
FiveGCAction,
FiveG-ProSeAuthorized,
FiveG-ProSePC5QoSParameters,
FiveG-S-TMSI,
GlobalRANNodeID,
GUAMI,
HandoverFlag,
HandoverType,
IAB-Authorized,
IABNodeIndication,
IAB-Supported,
IMSVoiceSupportIndicator,
IndexToRFSP,
InfoOnRecommendedCellsAndRANNodesForPaging,
IntersystemSONConfigurationTransfer,
LAI,
LocationReportingRequestType,
LTE-A2X-ServicesAuthorized,
LTEM-Indication,
LTEUESidelinkAggregateMaximumBitrate,
LTEV2XServicesAuthorized,
MaskedIMEISV,
MBS-AreaSessionID,
MBS-DistributionReleaseRequestTransfer,
MBS-DistributionSetupRequestTransfer,
MBS-DistributionSetupResponseTransfer,
MBS-DistributionSetupUnsuccessfulTransfer,
MBS-ServiceArea,
MBS-SessionID,
MBSSessionReleaseResponseTransfer,
MBSSessionSetupOrModFailureTransfer,
MBSSessionSetupOrModRequestTransfer,
MBSSessionSetupOrModResponseTransfer,
MDTPLMNList,
MDTPLMNModificationList,
MessageIdentifier,
MobileIAB-Authorized,
MobileIABNodeIndication,
MobileIAB-Supported,
MobilityRestrictionList,
MulticastGroupPagingAreaList,
MulticastSessionActivationRequestTransfer,
MulticastSessionDeactivationRequestTransfer,
MulticastSessionUpdateRequestTransfer,
NAS-PDU,
NASSecurityParametersFromNGRAN,
NB-IoT-DefaultPagingDRX,
NB-IoT-PagingDRX,
NB-IoT-Paging-eDRXInfo,
NB-IoT-UEPriority,
NetworkControlledRepeaterAuthorized,
NewSecurityContextInd,
NGRAN-CGI,
NGRAN-TNLAssociationToRemoveList,
NGRANTraceID,
NID,
NoPDUSessionIndication,
NotifySourceNGRANNode,
NPN-AccessInformation,
NR-A2X-ServicesAuthorized,
NR-CGI,
NR-PagingeDRXInformation,
NRPPa-PDU,
NRUESidelinkAggregateMaximumBitrate,
NRV2XServicesAuthorized,
NumberOfBroadcastsRequested,
OverloadResponse,
OverloadStartNSSAIList,
PagingAssisDataforCEcapabUE,
PagingCause,
PagingDRX,
PagingOrigin,
PagingPolicyDifferentiation,
PagingPriority,
Partially-Allowed-NSSAI,
PC5QoSParameters,
PDUSessionAggregateMaximumBitRate,
PDUSessionListMTCommHReq,
PDUSessionResourceAdmittedList,
PDUSessionResourceFailedToModifyListModCfm,
PDUSessionResourceFailedToModifyListModRes,
PDUSessionResourceFailedToResumeListRESReq,
PDUSessionResourceFailedToResumeListRESRes,
PDUSessionResourceFailedToSetupListCxtFail,
PDUSessionResourceFailedToSetupListCxtRes,
PDUSessionResourceFailedToSetupListHOAck,
PDUSessionResourceFailedToSetupListPSReq,
PDUSessionResourceFailedToSetupListSURes,
PDUSessionResourceHandoverList,
PDUSessionResourceListCxtRelCpl,
PDUSessionResourceListCxtRelReq,
PDUSessionResourceListHORqd,
PDUSessionResourceModifyListModCfm,
PDUSessionResourceModifyListModInd,
PDUSessionResourceModifyListModReq,
PDUSessionResourceModifyListModRes,
PDUSessionResourceNotifyList,
PDUSessionResourceReleasedListNot,
PDUSessionResourceReleasedListPSAck,
PDUSessionResourceReleasedListPSFail,
PDUSessionResourceReleasedListRelRes,
PDUSessionResourceResumeListRESReq,
PDUSessionResourceResumeListRESRes,
PDUSessionResourceSecondaryRATUsageList,
PDUSessionResourceSetupListCxtReq,
PDUSessionResourceSetupListCxtRes,
PDUSessionResourceSetupListHOReq,
PDUSessionResourceSetupListSUReq,
PDUSessionResourceSetupListSURes,
PDUSessionResourceSuspendListSUSReq,
PDUSessionResourceSwitchedList,
PDUSessionResourceToBeSwitchedDLList,
PDUSessionResourceToReleaseListHOCmd,
PDUSessionResourceToReleaseListRelCmd,
PEIPSassistanceInformation,
PLMNIdentity,
PLMNSupportList,
PrivacyIndicator,
PWSFailedCellIDList,
QMCConfigInfo,
QMCDeactivation,
RANNodeName,
RANPagingPriority,
RANStatusTransfer-TransparentContainer,
RANTimingSynchronisationStatusInfo,
RAN-TSSRequestType,
RAN-TSSScope,
RAN-UE-NGAP-ID,
RedCapIndication,
RedirectionVoiceFallback,
RelativeAMFCapacity,
RepetitionPeriod,
ResetType,
RGLevelWirelineAccessCharacteristics,
RIMInformationTransfer,
RoutingID,
RRCEstablishmentCause,
RRCInactiveTransitionReportRequest,
RRCState,
SecurityContext,
SecurityKey,
SerialNumber,
ServedGUAMIList,
SliceSupportList,
SLPositioningRangingServiceInfo,
S-NSSAI,
SONConfigurationTransfer,
SourceToTarget-AMFInformationReroute,
SourceToTarget-TransparentContainer,
SRVCCOperationPossible,
SupportedTAList,
Suspend-Request-Indication,
Suspend-Response-Indication,
TAI,
TAIListForPaging,
TAIListForRestart,
TargetID,
TargetNSSAIInformation,
TargettoSource-Failure-TransparentContainer,
TargetToSource-TransparentContainer,
TimeSyncAssistanceInfo,
TimeToWait,
TNLAssociationList,
TraceActivation,
TrafficLoadReductionIndication,
TransportLayerAddress,
UEAggregateMaximumBitRate,
UE-associatedLogicalNG-connectionList,
UECapabilityInfoRequest,
UEContextRequest,
UE-DifferentiationInfo,
UE-NGAP-IDs,
UEPagingIdentity,
UEPresenceInAreaOfInterestList,
UERadioCapability,
UERadioCapabilityForPaging,
UERadioCapabilityID,
UERetentionInformation,
UESecurityCapabilities,
UESliceMaximumBitRateList,
UE-UP-CIoT-Support,
UL-CP-SecurityInformation,
UnavailableGUAMIList,
URI-address,
UserLocationInformation,
WarningAreaCoordinates,
WarningAreaList,
WarningMessageContents,
WarningSecurityInfo,
WarningType,
WUS-Assistance-Information,
XrDeviceWith2Rx
FROM NGAP-IEs
PrivateIE-Container{},
ProtocolExtensionContainer{},
ProtocolIE-Container{},
ProtocolIE-ContainerList{},
ProtocolIE-ContainerPair{},
ProtocolIE-SingleContainer{},
NGAP-PRIVATE-IES,
NGAP-PROTOCOL-EXTENSION,
NGAP-PROTOCOL-IES,
NGAP-PROTOCOL-IES-PAIR
FROM NGAP-Containers
id-A2X-PC5-QoS-Parameters,
id-AerialUEsubscriptionInformation,
id-AllowedNSSAI,
id-AMFName,
id-AMFOverloadResponse,
id-AMFSetID,
id-AMF-TNLAssociationFailedToSetupList,
id-AMF-TNLAssociationSetupList,
id-AMF-TNLAssociationToAddList,
id-AMF-TNLAssociationToRemoveList,
id-AMF-TNLAssociationToUpdateList,
id-AMFTrafficLoadReductionIndication,
id-AMF-UE-NGAP-ID,
id-AssistanceDataForPaging,
id-AssociatedSessionID,
id-AUN3DeviceAccessInfo,
id-AuthenticatedIndication,
id-BroadcastCancelledAreaList,
id-BroadcastCompletedAreaList,
id-BroadcastTransportFailureTransfer,
id-BroadcastTransportRequestTransfer,
id-BroadcastTransportResponseTransfer,
id-CancelAllWarningMessages,
id-Cause,
id-CellIDListForRestart,
id-CEmodeBrestricted,
id-CEmodeBSupport-Indicator,
id-CNAssistedRANTuning,
id-ConcurrentWarningMessageInd,
id-CoreNetworkAssistanceInformationForInactive,
id-CriticalityDiagnostics,
id-DataCodingScheme,
id-DefaultPagingDRX,
id-DirectForwardingPathAvailability,
id-DL-CP-SecurityInformation,
id-DL-Signalling,
id-EarlyStatusTransfer-TransparentContainer,
id-EDT-Session,
id-EmergencyAreaIDListForRestart,
id-EmergencyFallbackIndicator,
id-ENDC-SONConfigurationTransferDL,
id-ENDC-SONConfigurationTransferUL,
id-EndIndication,
id-Enhanced-CoverageRestriction,
id-ERedCapIndication,
id-EUTRA-CGI,
id-EUTRA-PagingeDRXInformation,
id-Extended-AMFName,
id-Extended-ConnectedTime,
id-Extended-RANNodeName,
id-FiveGCAction,
id-FiveG-ProSeAuthorized,
id-FiveG-ProSePC5QoSParameters,
id-FiveG-ProSeUEPC5AggregateMaximumBitRate,
id-FiveG-S-TMSI,
id-GlobalRANNodeID,
id-GUAMI,
id-HandoverFlag,
id-HandoverType,
id-IAB-Authorized,
id-IABNodeIndication,
id-IAB-Supported,
id-IMSVoiceSupportIndicator,
id-IndexToRFSP,
id-InfoOnRecommendedCellsAndRANNodesForPaging,
id-IntersystemSONConfigurationTransferDL,
id-IntersystemSONConfigurationTransferUL,
id-LocationReportingRequestType,
id-LTE-A2X-ServicesAuthorized,
id-LTE-A2X-UE-PC5-AggregateMaximumBitRate,
id-LTEM-Indication,
id-LTEUESidelinkAggregateMaximumBitrate,
id-LTEV2XServicesAuthorized,
id-ManagementBasedMDTPLMNList,
id-ManagementBasedMDTPLMNModificationList,
id-MaskedIMEISV,
id-MBS-AreaSessionID,
id-MBS-DistributionReleaseRequestTransfer,
id-MBS-DistributionSetupRequestTransfer,
id-MBS-DistributionSetupResponseTransfer,
id-MBS-DistributionSetupUnsuccessfulTransfer,
id-MBS-ServiceArea,
id-MBS-SessionID,
id-MBSSessionModificationFailureTransfer,
id-MBSSessionModificationRequestTransfer,
id-MBSSessionModificationResponseTransfer,
id-MBSSessionReleaseResponseTransfer,
id-MBSSessionSetupFailureTransfer,
id-MBSSessionSetupRequestTransfer,
id-MBSSessionSetupResponseTransfer,
id-MessageIdentifier,
id-MobileIAB-Authorized,
id-MobileIABNodeIndication,
id-MobileIAB-Supported,
id-MobilityRestrictionList,
id-MulticastGroupPagingAreaList,
id-MulticastSessionActivationRequestTransfer,
id-MulticastSessionDeactivationRequestTransfer,
id-MulticastSessionUpdateRequestTransfer,
id-NASC,
id-NAS-PDU,
id-NASSecurityParametersFromNGRAN,
id-NB-IoT-DefaultPagingDRX,
id-NB-IoT-PagingDRX,
id-NB-IoT-Paging-eDRXInfo,
id-NB-IoT-UEPriority,
id-NetworkControlledRepeaterAuthorized,
id-NewAMF-UE-NGAP-ID,
id-NewGUAMI,
id-NewSecurityContextInd,
id-NGAP-Message,
id-NGRAN-CGI,
id-NGRAN-TNLAssociationToRemoveList,
id-NGRANTraceID,
id-NoPDUSessionIndication,
id-NotifySourceNGRANNode,
id-NPN-AccessInformation,
id-NR-A2X-ServicesAuthorized,
id-NR-A2X-UE-PC5-AggregateMaximumBitRate,
id-NR-PagingeDRXInformation,
id-NRPPa-PDU,
id-NRUESidelinkAggregateMaximumBitrate,
id-NRV2XServicesAuthorized,
id-NumberOfBroadcastsRequested,
id-OldAMF,
id-OverloadStartNSSAIList,
id-PagingAssisDataforCEcapabUE,
id-PagingCause,
id-PagingDRX,
id-PagingOrigin,
id-PagingPolicyDifferentiation,
id-PagingPriority,
id-Partially-Allowed-NSSAI,
id-PC5QoSParameters,
id-PDUSessionListMTCommHReq,
id-PDUSessionResourceAdmittedList,
id-PDUSessionResourceFailedToModifyListModCfm,
id-PDUSessionResourceFailedToModifyListModRes,
id-PDUSessionResourceFailedToResumeListRESReq,
id-PDUSessionResourceFailedToResumeListRESRes,
id-PDUSessionResourceFailedToSetupListCxtFail,
id-PDUSessionResourceFailedToSetupListCxtRes,
id-PDUSessionResourceFailedToSetupListHOAck,
id-PDUSessionResourceFailedToSetupListPSReq,
id-PDUSessionResourceFailedToSetupListSURes,
id-PDUSessionResourceHandoverList,
id-PDUSessionResourceListCxtRelCpl,
id-PDUSessionResourceListCxtRelReq,
id-PDUSessionResourceListHORqd,
id-PDUSessionResourceModifyListModCfm,
id-PDUSessionResourceModifyListModInd,
id-PDUSessionResourceModifyListModReq,
id-PDUSessionResourceModifyListModRes,
id-PDUSessionResourceNotifyList,
id-PDUSessionResourceReleasedListNot,
id-PDUSessionResourceReleasedListPSAck,
id-PDUSessionResourceReleasedListPSFail,
id-PDUSessionResourceReleasedListRelRes,
id-PDUSessionResourceResumeListRESReq,
id-PDUSessionResourceResumeListRESRes,
id-PDUSessionResourceSecondaryRATUsageList,
id-PDUSessionResourceSetupListCxtReq,
id-PDUSessionResourceSetupListCxtRes,
id-PDUSessionResourceSetupListHOReq,
id-PDUSessionResourceSetupListSUReq,
id-PDUSessionResourceSetupListSURes,
id-PDUSessionResourceSuspendListSUSReq,
id-PDUSessionResourceSwitchedList,
id-PDUSessionResourceToBeSwitchedDLList,
id-PDUSessionResourceToReleaseListHOCmd,
id-PDUSessionResourceToReleaseListRelCmd,
id-PEIPSassistanceInformation,
id-PLMNSupportList,
id-PrivacyIndicator,
id-PWSFailedCellIDList,
id-QMCConfigInfo,
id-QMCDeactivation,
id-RANNodeName,
id-RANPagingPriority,
id-RANStatusTransfer-TransparentContainer,
id-RANTimingSynchronisationStatusInfo,
id-RAN-TSSRequestType,
id-RAN-TSSScope,
id-RAN-UE-NGAP-ID,
id-RedCapIndication,
id-RedirectionVoiceFallback,
id-RelativeAMFCapacity,
id-RepetitionPeriod,
id-ResetType,
id-RGLevelWirelineAccessCharacteristics,
id-RIMInformationTransfer,
id-RoutingID,
id-RRCEstablishmentCause,
id-RRCInactiveTransitionReportRequest,
id-RRC-Resume-Cause,
id-RRCState,
id-SecurityContext,
id-SecurityKey,
id-SelectedNID,
id-SelectedPLMNIdentity,
id-SerialNumber,
id-ServedGUAMIList,
id-SliceSupportList,
id-S-NSSAI,
id-SONConfigurationTransferDL,
id-SONConfigurationTransferUL,
id-SourceAMF-UE-NGAP-ID,
id-SourceToTarget-AMFInformationReroute,
id-SourceToTarget-TransparentContainer,
id-SRVCCOperationPossible,
id-SupportedTAList,
id-Suspend-Request-Indication,
id-Suspend-Response-Indication,
id-TAI,
id-TAIListForPaging,
id-TAIListForRestart,
id-TargetID,
id-TargetNSSAIInformation,
id-TargettoSource-Failure-TransparentContainer,
id-TargetToSource-TransparentContainer,
id-TimeSyncAssistanceInfo,
id-TimeToWait,
id-TNGFIdentityInformation,
id-TraceActivation,
id-TraceCollectionEntityIPAddress,
id-TraceCollectionEntityURI,
id-TWIFIdentityInformation,
id-UEAggregateMaximumBitRate,
id-UE-associatedLogicalNG-connectionList,
id-UECapabilityInfoRequest,
id-UEContextRequest,
id-UE-DifferentiationInfo,
id-UE-NGAP-IDs,
id-UEPagingIdentity,
id-UEPresenceInAreaOfInterestList,
id-UERadioCapability,
id-UERadioCapability-EUTRA-Format,
id-UERadioCapabilityForPaging,
id-UERadioCapabilityID,
id-UERetentionInformation,
id-UESecurityCapabilities,
id-UESliceMaximumBitRateList,
id-UE-UP-CIoT-Support,
id-UL-CP-SecurityInformation,
id-UnavailableGUAMIList,
id-UserLocationInformation,
id-W-AGFIdentityInformation,
id-WarningAreaCoordinates,
id-WarningAreaList,
id-WarningMessageContents,
id-WarningSecurityInfo,
id-WarningType,
id-WUS-Assistance-Information,
id-XrDeviceWith2Rx,
id-SLPositioningRangingServiceInfo,
id-ExtendedOldAMF
FROM NGAP-Constants;
-- **************************************************************
--
-- PDU SESSION MANAGEMENT ELEMENTARY PROCEDURES
--
-- **************************************************************
-- **************************************************************
--
-- PDU Session Resource Setup Elementary Procedure
--
-- **************************************************************
-- **************************************************************
--
-- PDU SESSION RESOURCE SETUP REQUEST
--
-- **************************************************************
PDUSessionResourceSetupRequest ::= SEQUENCE {
protocolIEs ProtocolIE-Container { {PDUSessionResourceSetupRequestIEs} },
...
}
PDUSessionResourceSetupRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-NAS-PDU CRITICALITY reject TYPE NAS-PDU PRESENCE optional }|
{ ID id-PDUSessionResourceSetupListSUReq CRITICALITY reject TYPE PDUSessionResourceSetupListSUReq PRESENCE mandatory }|
{ ID id-UEAggregateMaximumBitRate CRITICALITY ignore TYPE UEAggregateMaximumBitRate PRESENCE optional }|
{ ID id-UESliceMaximumBitRateList CRITICALITY ignore TYPE UESliceMaximumBitRateList PRESENCE optional },
...
}
-- **************************************************************
--
-- PDU SESSION RESOURCE SETUP RESPONSE
--
-- **************************************************************
PDUSessionResourceSetupResponse ::= SEQUENCE {
protocolIEs ProtocolIE-Container { {PDUSessionResourceSetupResponseIEs} },
...
}
PDUSessionResourceSetupResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSetupListSURes CRITICALITY ignore TYPE PDUSessionResourceSetupListSURes PRESENCE optional }|
{ ID id-PDUSessionResourceFailedToSetupListSURes CRITICALITY ignore TYPE PDUSessionResourceFailedToSetupListSURes PRESENCE optional }|
{ ID id-CriticalityDiagnostics CRITICALITY ignore TYPE CriticalityDiagnostics PRESENCE optional }|
{ ID id-UserLocationInformation CRITICALITY ignore TYPE UserLocationInformation PRESENCE optional },
...
}
-- **************************************************************
--
-- PDU Session Resource Release Elementary Procedure
--
-- **************************************************************
-- **************************************************************
--
-- PDU SESSION RESOURCE RELEASE COMMAND
--
-- **************************************************************
PDUSessionResourceReleaseCommand ::= SEQUENCE {
protocolIEs ProtocolIE-Container { {PDUSessionResourceReleaseCommandIEs} },
...
}
PDUSessionResourceReleaseCommandIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-NAS-PDU CRITICALITY ignore TYPE NAS-PDU PRESENCE optional }|
{ ID id-PDUSessionResourceToReleaseListRelCmd CRITICALITY reject TYPE PDUSessionResourceToReleaseListRelCmd PRESENCE mandatory },
...
}
-- **************************************************************
--
-- PDU SESSION RESOURCE RELEASE RESPONSE
--
-- **************************************************************
PDUSessionResourceReleaseResponse ::= SEQUENCE {
protocolIEs ProtocolIE-Container { {PDUSessionResourceReleaseResponseIEs} },
...
}
PDUSessionResourceReleaseResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceReleasedListRelRes CRITICALITY ignore TYPE PDUSessionResourceReleasedListRelRes PRESENCE mandatory }|
{ ID id-UserLocationInformation CRITICALITY ignore TYPE UserLocationInformation PRESENCE optional }|
{ ID id-CriticalityDiagnostics CRITICALITY ignore TYPE CriticalityDiagnostics PRESENCE optional },
...
}
-- **************************************************************
--
-- PDU Session Resource Modify Elementary Procedure
--
-- **************************************************************
-- **************************************************************
--
-- PDU SESSION RESOURCE MODIFY REQUEST
--
-- **************************************************************
PDUSessionResourceModifyRequest ::= SEQUENCE {
protocolIEs ProtocolIE-Container { {PDUSessionResourceModifyRequestIEs} },
...
}
PDUSessionResourceModifyRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-PDUSessionResourceModifyListModReq CRITICALITY reject TYPE PDUSessionResourceModifyListModReq PRESENCE mandatory },
...
}
-- **************************************************************
--
-- PDU SESSION RESOURCE MODIFY RESPONSE
--
-- **************************************************************
PDUSessionResourceModifyResponse ::= SEQUENCE {
protocolIEs ProtocolIE-Container { {PDUSessionResourceModifyResponseIEs} },
...
}
PDUSessionResourceModifyResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceModifyListModRes CRITICALITY ignore TYPE PDUSessionResourceModifyListModRes PRESENCE optional }|
{ ID id-PDUSessionResourceFailedToModifyListModRes CRITICALITY ignore TYPE PDUSessionResourceFailedToModifyListModRes PRESENCE optional }|
{ ID id-UserLocationInformation CRITICALITY ignore TYPE UserLocationInformation PRESENCE optional }|
{ ID id-CriticalityDiagnostics CRITICALITY ignore TYPE CriticalityDiagnostics PRESENCE optional },
...
}
-- **************************************************************
--
-- PDU Session Resource Notify Elementary Procedure
--
-- **************************************************************
-- **************************************************************
--
-- PDU SESSION RESOURCE NOTIFY
--
-- **************************************************************
PDUSessionResourceNotify ::= SEQUENCE {
protocolIEs ProtocolIE-Container { {PDUSessionResourceNotifyIEs} },
...
}
PDUSessionResourceNotifyIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceNotifyList CRITICALITY reject TYPE PDUSessionResourceNotifyList PRESENCE optional }|
{ ID id-PDUSessionResourceReleasedListNot CRITICALITY ignore TYPE PDUSessionResourceReleasedListNot PRESENCE optional }|
{ ID id-UserLocationInformation CRITICALITY ignore TYPE UserLocationInformation PRESENCE optional },
...
}
-- **************************************************************
--
-- PDU Session Resource Modify Indication Elementary Procedure
--
-- **************************************************************
-- **************************************************************
--
-- PDU SESSION RESOURCE MODIFY INDICATION
--
-- **************************************************************
PDUSessionResourceModifyIndication ::= SEQUENCE {
protocolIEs ProtocolIE-Container { {PDUSessionResourceModifyIndicationIEs} },
...
}
PDUSessionResourceModifyIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceModifyListModInd CRITICALITY reject TYPE PDUSessionResourceModifyListModInd PRESENCE mandatory }|
{ ID id-UserLocationInformation CRITICALITY ignore TYPE UserLocationInformation PRESENCE optional },
...
}
-- **************************************************************
--
-- PDU SESSION RESOURCE MODIFY CONFIRM
--
-- **************************************************************
PDUSessionResourceModifyConfirm ::= SEQUENCE {
protocolIEs ProtocolIE-Container { {PDUSessionResourceModifyConfirmIEs} },
...
}
PDUSessionResourceModifyConfirmIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceModifyListModCfm CRITICALITY ignore TYPE PDUSessionResourceModifyListModCfm PRESENCE optional }|
{ ID id-PDUSessionResourceFailedToModifyListModCfm CRITICALITY ignore TYPE PDUSessionResourceFailedToModifyListModCfm PRESENCE optional }|
{ ID id-CriticalityDiagnostics CRITICALITY ignore TYPE CriticalityDiagnostics PRESENCE optional },
...
}
-- **************************************************************
--
-- UE CONTEXT MANAGEMENT ELEMENTARY PROCEDURES
--
-- **************************************************************
-- **************************************************************
--
-- Initial Context Setup Elementary Procedure
--
-- **************************************************************
-- **************************************************************
--
-- INITIAL CONTEXT SETUP REQUEST
--
-- **************************************************************
InitialContextSetupRequest ::= SEQUENCE {
protocolIEs ProtocolIE-Container { {InitialContextSetupRequestIEs} },
...
}
InitialContextSetupRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-OldAMF CRITICALITY reject TYPE AMFName PRESENCE optional }|
{ ID id-UEAggregateMaximumBitRate CRITICALITY reject TYPE UEAggregateMaximumBitRate PRESENCE conditional }|
-- The above IE shall be present if the PDU Session Resource Setup List IE is present
{ ID id-CoreNetworkAssistanceInformationForInactive CRITICALITY ignore TYPE CoreNetworkAssistanceInformationForInactive PRESENCE optional }|
{ ID id-GUAMI CRITICALITY reject TYPE GUAMI PRESENCE mandatory }|
{ ID id-PDUSessionResourceSetupListCxtReq CRITICALITY reject TYPE PDUSessionResourceSetupListCxtReq PRESENCE optional }|
{ ID id-AllowedNSSAI CRITICALITY reject TYPE AllowedNSSAI PRESENCE mandatory }|
{ ID id-UESecurityCapabilities CRITICALITY reject TYPE UESecurityCapabilities PRESENCE mandatory }|
{ ID id-SecurityKey CRITICALITY reject TYPE SecurityKey PRESENCE mandatory }|
{ ID id-TraceActivation CRITICALITY ignore TYPE TraceActivation PRESENCE optional }|
{ ID id-MobilityRestrictionList CRITICALITY ignore TYPE MobilityRestrictionList PRESENCE optional }|
{ ID id-UERadioCapability CRITICALITY ignore TYPE UERadioCapability PRESENCE optional }|
{ ID id-IndexToRFSP CRITICALITY ignore TYPE IndexToRFSP PRESENCE optional }|
{ ID id-MaskedIMEISV CRITICALITY ignore TYPE MaskedIMEISV PRESENCE optional }|
{ ID id-NAS-PDU CRITICALITY ignore TYPE NAS-PDU PRESENCE optional }|
{ ID id-EmergencyFallbackIndicator CRITICALITY reject TYPE EmergencyFallbackIndicator PRESENCE optional }|
{ ID id-RRCInactiveTransitionReportRequest CRITICALITY ignore TYPE RRCInactiveTransitionReportRequest PRESENCE optional }|
{ ID id-UERadioCapabilityForPaging CRITICALITY ignore TYPE UERadioCapabilityForPaging PRESENCE optional }|
{ ID id-RedirectionVoiceFallback CRITICALITY ignore TYPE RedirectionVoiceFallback PRESENCE optional }|
{ ID id-LocationReportingRequestType CRITICALITY ignore TYPE LocationReportingRequestType PRESENCE optional }|
{ ID id-CNAssistedRANTuning CRITICALITY ignore TYPE CNAssistedRANTuning PRESENCE optional }|
{ ID id-SRVCCOperationPossible CRITICALITY ignore TYPE SRVCCOperationPossible PRESENCE optional }|
{ ID id-IAB-Authorized CRITICALITY ignore TYPE IAB-Authorized PRESENCE optional }|
{ ID id-Enhanced-CoverageRestriction CRITICALITY ignore TYPE Enhanced-CoverageRestriction PRESENCE optional }|
{ ID id-Extended-ConnectedTime CRITICALITY ignore TYPE Extended-ConnectedTime PRESENCE optional }|
{ ID id-UE-DifferentiationInfo CRITICALITY ignore TYPE UE-DifferentiationInfo PRESENCE optional }|
{ ID id-NRV2XServicesAuthorized CRITICALITY ignore TYPE NRV2XServicesAuthorized PRESENCE optional }|
{ ID id-LTEV2XServicesAuthorized CRITICALITY ignore TYPE LTEV2XServicesAuthorized PRESENCE optional }|
{ ID id-NRUESidelinkAggregateMaximumBitrate CRITICALITY ignore TYPE NRUESidelinkAggregateMaximumBitrate PRESENCE optional }|
{ ID id-LTEUESidelinkAggregateMaximumBitrate CRITICALITY ignore TYPE LTEUESidelinkAggregateMaximumBitrate PRESENCE optional }|
{ ID id-PC5QoSParameters CRITICALITY ignore TYPE PC5QoSParameters PRESENCE optional }|
{ ID id-CEmodeBrestricted CRITICALITY ignore TYPE CEmodeBrestricted PRESENCE optional }|
{ ID id-UE-UP-CIoT-Support CRITICALITY ignore TYPE UE-UP-CIoT-Support PRESENCE optional }|
{ ID id-RGLevelWirelineAccessCharacteristics CRITICALITY ignore TYPE RGLevelWirelineAccessCharacteristics PRESENCE optional }|
{ ID id-ManagementBasedMDTPLMNList CRITICALITY ignore TYPE MDTPLMNList PRESENCE optional }|
{ ID id-UERadioCapabilityID CRITICALITY reject TYPE UERadioCapabilityID PRESENCE optional }|
{ ID id-TimeSyncAssistanceInfo CRITICALITY ignore TYPE TimeSyncAssistanceInfo PRESENCE optional }|
{ ID id-QMCConfigInfo CRITICALITY ignore TYPE QMCConfigInfo PRESENCE optional }|
{ ID id-TargetNSSAIInformation CRITICALITY ignore TYPE TargetNSSAIInformation PRESENCE optional }|
{ ID id-UESliceMaximumBitRateList CRITICALITY ignore TYPE UESliceMaximumBitRateList PRESENCE optional }|
{ ID id-FiveG-ProSeAuthorized CRITICALITY ignore TYPE FiveG-ProSeAuthorized PRESENCE optional }|
{ ID id-FiveG-ProSeUEPC5AggregateMaximumBitRate CRITICALITY ignore TYPE NRUESidelinkAggregateMaximumBitrate PRESENCE optional }|
{ ID id-FiveG-ProSePC5QoSParameters CRITICALITY ignore TYPE FiveG-ProSePC5QoSParameters PRESENCE optional }|
{ ID id-NetworkControlledRepeaterAuthorized CRITICALITY ignore TYPE NetworkControlledRepeaterAuthorized PRESENCE optional }|
{ ID id-AerialUEsubscriptionInformation CRITICALITY ignore TYPE AerialUEsubscriptionInformation PRESENCE optional }|
{ ID id-NR-A2X-ServicesAuthorized CRITICALITY ignore TYPE NR-A2X-ServicesAuthorized PRESENCE optional }|
{ ID id-LTE-A2X-ServicesAuthorized CRITICALITY ignore TYPE LTE-A2X-ServicesAuthorized PRESENCE optional }|
{ ID id-NR-A2X-UE-PC5-AggregateMaximumBitRate CRITICALITY ignore TYPE NRUESidelinkAggregateMaximumBitrate PRESENCE optional }|
{ ID id-LTE-A2X-UE-PC5-AggregateMaximumBitRate CRITICALITY ignore TYPE LTEUESidelinkAggregateMaximumBitrate PRESENCE optional }|
{ ID id-A2X-PC5-QoS-Parameters CRITICALITY ignore TYPE A2X-PC5-QoS-Parameters PRESENCE optional }|
{ ID id-MobileIAB-Authorized CRITICALITY ignore TYPE MobileIAB-Authorized PRESENCE optional }|
{ ID id-Partially-Allowed-NSSAI CRITICALITY ignore TYPE Partially-Allowed-NSSAI PRESENCE optional }|
{ ID id-SLPositioningRangingServiceInfo CRITICALITY ignore TYPE SLPositioningRangingServiceInfo PRESENCE optional }|
{ ID id-ExtendedOldAMF CRITICALITY ignore TYPE Extended-AMFName PRESENCE optional },
...
}
-- **************************************************************
--
-- INITIAL CONTEXT SETUP RESPONSE
--
-- **************************************************************
InitialContextSetupResponse ::= SEQUENCE {
protocolIEs ProtocolIE-Container { {InitialContextSetupResponseIEs} },
...
}
InitialContextSetupResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSetupListCxtRes CRITICALITY ignore TYPE PDUSessionResourceSetupListCxtRes PRESENCE optional }|
{ ID id-PDUSessionResourceFailedToSetupListCxtRes CRITICALITY ignore TYPE PDUSessionResourceFailedToSetupListCxtRes PRESENCE optional }|
{ ID id-CriticalityDiagnostics CRITICALITY ignore TYPE CriticalityDiagnostics PRESENCE optional },
...
}
-- **************************************************************
--
-- INITIAL CONTEXT SETUP FAILURE
--
-- **************************************************************
InitialContextSetupFailure ::= SEQUENCE {
protocolIEs ProtocolIE-Container { {InitialContextSetupFailureIEs} },
...
}
InitialContextSetupFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceFailedToSetupListCxtFail CRITICALITY ignore TYPE PDUSessionResourceFailedToSetupListCxtFail PRESENCE optional }|
{ ID id-Cause CRITICALITY ignore TYPE Cause PRESENCE mandatory }|
{ ID id-CriticalityDiagnostics CRITICALITY ignore TYPE CriticalityDiagnostics PRESENCE optional },
...
}
-- **************************************************************
--
-- UE Context Release Request Elementary Procedure
--
-- **************************************************************
-- **************************************************************
--
-- UE CONTEXT RELEASE REQUEST
--
-- **************************************************************
UEContextReleaseRequest ::= SEQUENCE {
protocolIEs ProtocolIE-Container { {UEContextReleaseRequest-IEs} },
...
}
UEContextReleaseRequest-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-PDUSessionResourceListCxtRelReq CRITICALITY reject TYPE PDUSessionResourceListCxtRelReq PRESENCE optional }|
{ ID id-Cause CRITICALITY ignore TYPE Cause PRESENCE mandatory },
...
}
-- **************************************************************
--
-- UE Context Release Elementary Procedure
--
-- **************************************************************
-- **************************************************************
--
-- UE CONTEXT RELEASE COMMAND
--
-- **************************************************************
UEContextReleaseCommand ::= SEQUENCE {
protocolIEs ProtocolIE-Container { {UEContextReleaseCommand-IEs} },
...
}
UEContextReleaseCommand-IEs NGAP-PROTOCOL-IES ::= {
{ ID id-UE-NGAP-IDs CRITICALITY reject TYPE UE-NGAP-IDs PRESENCE mandatory }|
{ ID id-Cause CRITICALITY ignore TYPE Cause PRESENCE mandatory },
...
}
-- **************************************************************
--
-- UE CONTEXT RELEASE COMPLETE
--
-- **************************************************************
UEContextReleaseComplete ::= SEQUENCE {
protocolIEs ProtocolIE-Container { {UEContextReleaseComplete-IEs} },
...
}
UEContextReleaseComplete-IEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-UserLocationInformation CRITICALITY ignore TYPE UserLocationInformation PRESENCE optional }|
{ ID id-InfoOnRecommendedCellsAndRANNodesForPaging CRITICALITY ignore TYPE InfoOnRecommendedCellsAndRANNodesForPaging PRESENCE optional }|
{ ID id-PDUSessionResourceListCxtRelCpl CRITICALITY reject TYPE PDUSessionResourceListCxtRelCpl PRESENCE optional }|
{ ID id-CriticalityDiagnostics CRITICALITY ignore TYPE CriticalityDiagnostics PRESENCE optional }|
{ ID id-PagingAssisDataforCEcapabUE CRITICALITY ignore TYPE PagingAssisDataforCEcapabUE PRESENCE optional },
...
}
-- **************************************************************
--
-- UE Context Resume Elementary Procedure
--
-- **************************************************************
-- **************************************************************
--
-- UE CONTEXT RESUME REQUEST
--
-- **************************************************************
UEContextResumeRequest ::= SEQUENCE {
protocolIEs ProtocolIE-Container { {UEContextResumeRequestIEs} },
...
}
UEContextResumeRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RRC-Resume-Cause CRITICALITY ignore TYPE RRCEstablishmentCause PRESENCE mandatory }|
{ ID id-PDUSessionResourceResumeListRESReq CRITICALITY reject TYPE PDUSessionResourceResumeListRESReq PRESENCE optional }|
{ ID id-PDUSessionResourceFailedToResumeListRESReq CRITICALITY reject TYPE PDUSessionResourceFailedToResumeListRESReq PRESENCE optional }|
{ ID id-Suspend-Request-Indication CRITICALITY ignore TYPE Suspend-Request-Indication PRESENCE optional }|
{ ID id-InfoOnRecommendedCellsAndRANNodesForPaging CRITICALITY ignore TYPE InfoOnRecommendedCellsAndRANNodesForPaging PRESENCE optional }|
{ ID id-PagingAssisDataforCEcapabUE CRITICALITY ignore TYPE PagingAssisDataforCEcapabUE PRESENCE optional }|
{ ID id-UserLocationInformation CRITICALITY ignore TYPE UserLocationInformation PRESENCE optional },
...
}
-- **************************************************************
--
-- UE CONTEXT RESUME RESPONSE
--
-- **************************************************************
UEContextResumeResponse ::= SEQUENCE {
protocolIEs ProtocolIE-Container { {UEContextResumeResponseIEs} },
...
}
UEContextResumeResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceResumeListRESRes CRITICALITY reject TYPE PDUSessionResourceResumeListRESRes PRESENCE optional }|
{ ID id-PDUSessionResourceFailedToResumeListRESRes CRITICALITY reject TYPE PDUSessionResourceFailedToResumeListRESRes PRESENCE optional }|
{ ID id-SecurityContext CRITICALITY reject TYPE SecurityContext PRESENCE optional }|
{ ID id-Suspend-Response-Indication CRITICALITY ignore TYPE Suspend-Response-Indication PRESENCE optional }|
{ ID id-Extended-ConnectedTime CRITICALITY ignore TYPE Extended-ConnectedTime PRESENCE optional }|
{ ID id-CriticalityDiagnostics CRITICALITY ignore TYPE CriticalityDiagnostics PRESENCE optional },
...
}
-- **************************************************************
--
-- UE CONTEXT RESUME FAILURE
--
-- **************************************************************
UEContextResumeFailure ::= SEQUENCE {
protocolIEs ProtocolIE-Container { { UEContextResumeFailureIEs} },
...
}
UEContextResumeFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- UE Context Suspend Elementary Procedure
--
-- **************************************************************
-- **************************************************************
--
-- UE CONTEXT SUSPEND REQUEST
--
-- **************************************************************
UEContextSuspendRequest ::= SEQUENCE {
protocolIEs ProtocolIE-Container { {UEContextSuspendRequestIEs} },
...
}
UEContextSuspendRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-InfoOnRecommendedCellsAndRANNodesForPaging CRITICALITY ignore TYPE InfoOnRecommendedCellsAndRANNodesForPaging PRESENCE optional }|
{ ID id-PagingAssisDataforCEcapabUE CRITICALITY ignore TYPE PagingAssisDataforCEcapabUE PRESENCE optional }|
{ ID id-PDUSessionResourceSuspendListSUSReq CRITICALITY reject TYPE PDUSessionResourceSuspendListSUSReq PRESENCE optional }|
{ ID id-UserLocationInformation CRITICALITY ignore TYPE UserLocationInformation PRESENCE optional },
...
}
-- **************************************************************
--
-- UE CONTEXT SUSPEND RESPONSE
--
-- **************************************************************
UEContextSuspendResponse ::= SEQUENCE {
protocolIEs ProtocolIE-Container { {UEContextSuspendResponseIEs} },
...
}
UEContextSuspendResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-SecurityContext CRITICALITY reject TYPE SecurityContext PRESENCE optional }|
{ ID id-CriticalityDiagnostics CRITICALITY ignore TYPE CriticalityDiagnostics PRESENCE optional },
...
}
-- **************************************************************
--
-- UE CONTEXT SUSPEND FAILURE
--
-- **************************************************************
UEContextSuspendFailure ::= SEQUENCE {
protocolIEs ProtocolIE-Container { { UEContextSuspendFailureIEs} },
...
}
UEContextSuspendFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- UE Context Modification Elementary Procedure
--
-- **************************************************************
-- **************************************************************
--
-- UE CONTEXT MODIFICATION REQUEST
--
-- **************************************************************
UEContextModificationRequest ::= SEQUENCE {
protocolIEs ProtocolIE-Container { {UEContextModificationRequestIEs} },
...
}
UEContextModificationRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANPagingPriority CRITICALITY ignore TYPE RANPagingPriority PRESENCE optional }|
{ ID id-SecurityKey CRITICALITY reject TYPE SecurityKey PRESENCE optional }|
{ ID id-IndexToRFSP CRITICALITY ignore TYPE IndexToRFSP PRESENCE optional }|
{ ID id-UEAggregateMaximumBitRate CRITICALITY ignore TYPE UEAggregateMaximumBitRate PRESENCE optional }|
{ ID id-UESecurityCapabilities CRITICALITY reject TYPE UESecurityCapabilities PRESENCE optional }|
{ ID id-CoreNetworkAssistanceInformationForInactive CRITICALITY ignore TYPE CoreNetworkAssistanceInformationForInactive PRESENCE optional }|
{ ID id-EmergencyFallbackIndicator CRITICALITY reject TYPE EmergencyFallbackIndicator PRESENCE optional }|
{ ID id-NewAMF-UE-NGAP-ID CRITICALITY reject TYPE AMF-UE-NGAP-ID PRESENCE optional }|
{ ID id-RRCInactiveTransitionReportRequest CRITICALITY ignore TYPE RRCInactiveTransitionReportRequest PRESENCE optional }|
{ ID id-NewGUAMI CRITICALITY reject TYPE GUAMI PRESENCE optional }|
{ ID id-CNAssistedRANTuning CRITICALITY ignore TYPE CNAssistedRANTuning PRESENCE optional }|
{ ID id-SRVCCOperationPossible CRITICALITY ignore TYPE SRVCCOperationPossible PRESENCE optional }|
{ ID id-IAB-Authorized CRITICALITY ignore TYPE IAB-Authorized PRESENCE optional }|
{ ID id-NRV2XServicesAuthorized CRITICALITY ignore TYPE NRV2XServicesAuthorized PRESENCE optional }|
{ ID id-LTEV2XServicesAuthorized CRITICALITY ignore TYPE LTEV2XServicesAuthorized PRESENCE optional }|
{ ID id-NRUESidelinkAggregateMaximumBitrate CRITICALITY ignore TYPE NRUESidelinkAggregateMaximumBitrate PRESENCE optional }|
{ ID id-LTEUESidelinkAggregateMaximumBitrate CRITICALITY ignore TYPE LTEUESidelinkAggregateMaximumBitrate PRESENCE optional }|
{ ID id-PC5QoSParameters CRITICALITY ignore TYPE PC5QoSParameters PRESENCE optional }|
{ ID id-UERadioCapabilityID CRITICALITY reject TYPE UERadioCapabilityID PRESENCE optional }|
{ ID id-RGLevelWirelineAccessCharacteristics CRITICALITY ignore TYPE RGLevelWirelineAccessCharacteristics PRESENCE optional }|
{ ID id-TimeSyncAssistanceInfo CRITICALITY ignore TYPE TimeSyncAssistanceInfo PRESENCE optional }|
{ ID id-QMCConfigInfo CRITICALITY ignore TYPE QMCConfigInfo PRESENCE optional }|
{ ID id-QMCDeactivation CRITICALITY ignore TYPE QMCDeactivation PRESENCE optional }|
{ ID id-UESliceMaximumBitRateList CRITICALITY ignore TYPE UESliceMaximumBitRateList PRESENCE optional }|
{ ID id-ManagementBasedMDTPLMNModificationList CRITICALITY ignore TYPE MDTPLMNModificationList PRESENCE optional }|
{ ID id-FiveG-ProSeAuthorized CRITICALITY ignore TYPE FiveG-ProSeAuthorized PRESENCE optional }|
{ ID id-FiveG-ProSeUEPC5AggregateMaximumBitRate CRITICALITY ignore TYPE NRUESidelinkAggregateMaximumBitrate PRESENCE optional }|
{ ID id-FiveG-ProSePC5QoSParameters CRITICALITY ignore TYPE FiveG-ProSePC5QoSParameters PRESENCE optional }|
{ ID id-NetworkControlledRepeaterAuthorized CRITICALITY ignore TYPE NetworkControlledRepeaterAuthorized PRESENCE optional }|
{ ID id-AerialUEsubscriptionInformation CRITICALITY ignore TYPE AerialUEsubscriptionInformation PRESENCE optional }|
{ ID id-NR-A2X-ServicesAuthorized CRITICALITY ignore TYPE NR-A2X-ServicesAuthorized PRESENCE optional }|
{ ID id-LTE-A2X-ServicesAuthorized CRITICALITY ignore TYPE LTE-A2X-ServicesAuthorized PRESENCE optional }|
{ ID id-NR-A2X-UE-PC5-AggregateMaximumBitRate CRITICALITY ignore TYPE NRUESidelinkAggregateMaximumBitrate PRESENCE optional }|
{ ID id-LTE-A2X-UE-PC5-AggregateMaximumBitRate CRITICALITY ignore TYPE LTEUESidelinkAggregateMaximumBitrate PRESENCE optional }|
{ ID id-A2X-PC5-QoS-Parameters CRITICALITY ignore TYPE A2X-PC5-QoS-Parameters PRESENCE optional }|
{ ID id-MobileIAB-Authorized CRITICALITY ignore TYPE MobileIAB-Authorized PRESENCE optional }|
{ ID id-SLPositioningRangingServiceInfo CRITICALITY ignore TYPE SLPositioningRangingServiceInfo PRESENCE optional },
...
}
-- **************************************************************
--
-- UE CONTEXT MODIFICATION RESPONSE
--
-- **************************************************************
UEContextModificationResponse ::= SEQUENCE {
protocolIEs ProtocolIE-Container { {UEContextModificationResponseIEs} },
...
}
UEContextModificationResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-RRCState CRITICALITY ignore TYPE RRCState PRESENCE optional }|
{ ID id-UserLocationInformation CRITICALITY ignore TYPE UserLocationInformation PRESENCE optional }|
{ ID id-CriticalityDiagnostics CRITICALITY ignore TYPE CriticalityDiagnostics PRESENCE optional },
...
}
-- **************************************************************
--
-- UE CONTEXT MODIFICATION FAILURE
--
-- **************************************************************
UEContextModificationFailure ::= SEQUENCE {
protocolIEs ProtocolIE-Container { {UEContextModificationFailureIEs} },
...
}
UEContextModificationFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
--
-- RRC INACTIVE TRANSITION REPORT
--
-- **************************************************************
RRCInactiveTransitionReport ::= SEQUENCE {
protocolIEs ProtocolIE-Container { {RRCInactiveTransitionReportIEs} },
...
}
RRCInactiveTransitionReportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RRCState CRITICALITY ignore TYPE RRCState PRESENCE mandatory }|
{ ID id-UserLocationInformation CRITICALITY ignore TYPE UserLocationInformation PRESENCE mandatory },
...
}
-- **************************************************************
--
-- Retrieve UE Information
--
-- **************************************************************
RetrieveUEInformation ::= SEQUENCE {
protocolIEs ProtocolIE-Container { { RetrieveUEInformationIEs} },
...
}
RetrieveUEInformationIEs NGAP-PROTOCOL-IES ::= {
{ ID id-FiveG-S-TMSI CRITICALITY reject TYPE FiveG-S-TMSI PRESENCE mandatory },
...
}
-- **************************************************************
-- UE Information Transfer
--
-- **************************************************************
UEInformationTransfer ::= SEQUENCE {
protocolIEs ProtocolIE-Container { { UEInformationTransferIEs} },
...
}
UEInformationTransferIEs NGAP-PROTOCOL-IES ::= {
{ ID id-FiveG-S-TMSI CRITICALITY reject TYPE FiveG-S-TMSI PRESENCE mandatory }|
{ ID id-NB-IoT-UEPriority CRITICALITY ignore TYPE NB-IoT-UEPriority PRESENCE optional }|
{ ID id-UERadioCapability CRITICALITY ignore TYPE UERadioCapability PRESENCE optional }|
{ ID id-S-NSSAI CRITICALITY ignore TYPE S-NSSAI PRESENCE optional }|
{ ID id-AllowedNSSAI CRITICALITY ignore TYPE AllowedNSSAI PRESENCE optional }|
{ ID id-UE-DifferentiationInfo CRITICALITY ignore TYPE UE-DifferentiationInfo PRESENCE optional }|
{ ID id-MaskedIMEISV CRITICALITY ignore TYPE MaskedIMEISV PRESENCE optional }|
{ ID id-Partially-Allowed-NSSAI CRITICALITY ignore TYPE Partially-Allowed-NSSAI PRESENCE optional },
...
}
-- **************************************************************
--
-- RAN CP Relocation Indication
--
-- **************************************************************
RANCPRelocationIndication ::= SEQUENCE {
protocolIEs ProtocolIE-Container { { RANCPRelocationIndicationIEs} },
...
}
RANCPRelocationIndicationIEs NGAP-PROTOCOL-IES ::= {
{ ID id-RAN-UE-NGAP-ID CRITICALITY reject TYPE RAN-UE-NGAP-ID PRESENCE mandatory }|
{ ID id-FiveG-S-TMSI CRITICALITY reject TYPE FiveG-S-TMSI PRESENCE mandatory }|
{ ID id-EUTRA-CGI CRITICALITY ignore TYPE EUTRA-CGI PRESENCE mandatory }|
{ ID id-TAI CRITICALITY ignore TYPE TAI PRESENCE mandatory }|
{ ID id-UL-CP-SecurityInformation CRITICALITY reject TYPE UL-CP-SecurityInformation PRESENCE mandatory },
...
}
-- **************************************************************
--
-- UE MOBILITY MANAGEMENT ELEMENTARY PROCEDURES
--
-- **************************************************************
-- **************************************************************
--
-- Handover Preparation Elementary Procedure
--
-- **************************************************************
-- **************************************************************
--
-- HANDOVER REQUIRED
--
-- **************************************************************
HandoverRequired ::= SEQUENCE {
protocolIEs ProtocolIE-Container { {HandoverRequiredIEs} },
...
}
HandoverRequiredIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-HandoverType CRITICALITY reject TYPE HandoverType PRESENCE mandatory }|
{ ID id-Cause CRITICALITY ignore TYPE Cause PRESENCE mandatory }|
{ ID id-TargetID CRITICALITY reject TYPE TargetID PRESENCE mandatory }|
{ ID id-DirectForwardingPathAvailability CRITICALITY ignore TYPE DirectForwardingPathAvailability PRESENCE optional }|
{ ID id-PDUSessionResourceListHORqd CRITICALITY reject TYPE PDUSessionResourceListHORqd PRESENCE mandatory }|
{ ID id-SourceToTarget-TransparentContainer CRITICALITY reject TYPE SourceToTarget-TransparentContainer PRESENCE mandatory },
...
}
-- **************************************************************
--
-- HANDOVER COMMAND
--
-- **************************************************************
HandoverCommand ::= SEQUENCE {
protocolIEs ProtocolIE-Container { {HandoverCommandIEs} },
...
}
HandoverCommandIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-HandoverType CRITICALITY reject TYPE HandoverType PRESENCE mandatory }|
{ ID id-NASSecurityParametersFromNGRAN CRITICALITY reject TYPE NASSecurityParametersFromNGRAN PRESENCE conditional }|
-- The above IE shall be present if the HandoverType IE is set to the value "5GStoEPPS" or "5GStoUTRAN"
{ ID id-PDUSessionResourceHandoverList CRITICALITY ignore TYPE PDUSessionResourceHandoverList PRESENCE optional }|
{ ID id-PDUSessionResourceToReleaseListHOCmd CRITICALITY ignore TYPE PDUSessionResourceToReleaseListHOCmd PRESENCE optional }|
{ ID id-TargetToSource-TransparentContainer CRITICALITY reject TYPE TargetToSource-TransparentContainer PRESENCE mandatory }|
{ ID id-CriticalityDiagnostics CRITICALITY ignore TYPE CriticalityDiagnostics PRESENCE optional },
...
}
-- **************************************************************
--
-- HANDOVER PREPARATION FAILURE
--
-- **************************************************************
HandoverPreparationFailure ::= SEQUENCE {
protocolIEs ProtocolIE-Container { {HandoverPreparationFailureIEs} },
...
}
HandoverPreparationFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-Cause CRITICALITY ignore TYPE Cause PRESENCE mandatory }|
{ ID id-CriticalityDiagnostics CRITICALITY ignore TYPE CriticalityDiagnostics PRESENCE optional }|
{ ID id-TargettoSource-Failure-TransparentContainer CRITICALITY ignore TYPE TargettoSource-Failure-TransparentContainer PRESENCE optional },
...
}
-- **************************************************************
--
-- Handover Resource Allocation Elementary Procedure
--
-- **************************************************************
-- **************************************************************
--
-- HANDOVER REQUEST
--
-- **************************************************************
HandoverRequest ::= SEQUENCE {
protocolIEs ProtocolIE-Container { {HandoverRequestIEs} },
...
}
HandoverRequestIEs NGAP-PROTOCOL-IES ::= {
{ ID id-AMF-UE-NGAP-ID CRITICALITY reject TYPE AMF-UE-NGAP-ID PRESENCE mandatory }|
{ ID id-HandoverType CRITICALITY reject TYPE HandoverType PRESENCE mandatory }|
{ ID id-Cause CRITICALITY ignore TYPE Cause PRESENCE mandatory }|
{ ID id-UEAggregateMaximumBitRate CRITICALITY reject TYPE UEAggregateMaximumBitRate PRESENCE mandatory }|
{ ID id-CoreNetworkAssistanceInformationForInactive CRITICALITY ignore TYPE CoreNetworkAssistanceInformationForInactive PRESENCE optional }|
{ ID id-UESecurityCapabilities CRITICALITY reject TYPE UESecurityCapabilities PRESENCE mandatory }|
{ ID id-SecurityContext CRITICALITY reject TYPE SecurityContext PRESENCE mandatory }|
{ ID id-NewSecurityContextInd CRITICALITY reject TYPE NewSecurityContextInd PRESENCE optional }|
{ ID id-NASC CRITICALITY reject TYPE NAS-PDU PRESENCE optional }|
{ ID id-PDUSessionResourceSetupListHOReq CRITICALITY reject TYPE PDUSessionResourceSetupListHOReq PRESENCE mandatory }|
{ ID id-AllowedNSSAI CRITICALITY reject TYPE AllowedNSSAI PRESENCE mandatory }|
{ ID id-TraceActivation CRITICALITY ignore TYPE TraceActivation PRESENCE optional }|
{ ID id-MaskedIMEISV CRITICALITY ignore TYPE MaskedIMEISV PRESENCE optional }|
{ ID id-SourceToTarget-TransparentContainer CRITICALITY reject TYPE SourceToTarget-TransparentContainer PRESENCE mandatory }|
{ ID id-MobilityRestrictionList CRITICALITY ignore TYPE MobilityRestrictionList PRESENCE optional }|
{ ID id-LocationReportingRequestType CRITICALITY ignore TYPE LocationReportingRequestType PRESENCE optional }|
{ ID id-RRCInactiveTransitionReportRequest CRITICALITY ignore TYPE RRCInactiveTransitionReportRequest PRESENCE optional }|
{ ID id-GUAMI CRITICALITY reject TYPE GUAMI PRESENCE mandatory }|
{ ID id-RedirectionVoiceFallback CRITICALITY ignore TYPE RedirectionVoiceFallback PRESENCE optional }|
{ ID id-CNAssistedRANTuning CRITICALITY ignore TYPE CNAssistedRANTuning PRESENCE optional }|
{ ID id-SRVCCOperationPossible CRITICALITY ignore TYPE SRVCCOperationPossible PRESENCE optional }|
{ ID id-IAB-Authorized CRITICALITY reject TYPE IAB-Authorized PRESENCE optional }|
{ ID id-Enhanced-CoverageRestriction CRITICALITY ignore TYPE Enhanced-CoverageRestriction PRESENCE optional }|
{ ID id-UE-DifferentiationInfo CRITICALITY ignore TYPE UE-DifferentiationInfo PRESENCE optional }|
{ ID id-NRV2XServicesAuthorized CRITICALITY ignore TYPE NRV2XServicesAuthorized PRESENCE optional }|
{ ID id-LTEV2XServicesAuthorized CRITICALITY ignore TYPE LTEV2XServicesAuthorized PRESENCE optional }|
{ ID id-NRUESidelinkAggregateMaximumBitrate CRITICALITY ignore TYPE NRUESidelinkAggregateMaximumBitrate PRESENCE optional }|
{ ID id-LTEUESidelinkAggregateMaximumBitrate CRITICALITY ignore TYPE LTEUESidelinkAggregateMaximumBitrate PRESENCE optional }|
{ ID id-PC5QoSParameters CRITICALITY ignore TYPE PC5QoSParameters PRESENCE optional }|
{ ID id-CEmodeBrestricted CRITICALITY ignore TYPE CEmodeBrestricted PRESENCE optional }|
{ ID id-UE-UP-CIoT-Support CRITICALITY ignore TYPE UE-UP-CIoT-Support PRESENCE optional }|
{ ID id-ManagementBasedMDTPLMNList CRITICALITY ignore TYPE MDTPLMNList PRESENCE optional }|
{ ID id-UERadioCapabilityID CRITICALITY reject TYPE UERadioCapabilityID PRESENCE optional }|
{ ID id-Extended-ConnectedTime CRITICALITY ignore TYPE Extended-ConnectedTime PRESENCE optional }|
{ ID id-TimeSyncAssistanceInfo CRITICALITY ignore TYPE TimeSyncAssistanceInfo PRESENCE optional }|
{ ID id-UESliceMaximumBitRateList CRITICALITY ignore TYPE UESliceMaximumBitRateList PRESENCE optional }|
{ ID id-FiveG-ProSeAuthorized CRITICALITY ignore TYPE FiveG-ProSeAuthorized PRESENCE optional }|
{ ID id-FiveG-ProSeUEPC5AggregateMaximumBitRate CRITICALITY ignore TYPE NRUESidelinkAggregateMaximumBitrate PRESENCE optional }|
{ ID id-FiveG-ProSePC5QoSParameters CRITICALITY ignore TYPE FiveG-ProSePC5QoSParameters PRESENCE optional }|
{ ID id-AerialUEsubscriptionInformation CRITICALITY ignore TYPE AerialUEsubscriptionInformation PRESENCE optional }|
{ ID id-NR-A2X-ServicesAuthorized CRITICALITY ignore TYPE NR-A2X-ServicesAuthorized PRESENCE optional }|
{ ID id-LTE-A2X-ServicesAuthorized CRITICALITY ignore TYPE LTE-A2X-ServicesAuthorized PRESENCE optional }|
{ ID id-NR-A2X-UE-PC5-AggregateMaximumBitRate CRITICALITY ignore TYPE NRUESidelinkAggregateMaximumBitrate PRESENCE optional }|
{ ID id-LTE-A2X-UE-PC5-AggregateMaximumBitRate CRITICALITY ignore TYPE LTEUESidelinkAggregateMaximumBitrate PRESENCE optional }|
{ ID id-A2X-PC5-QoS-Parameters CRITICALITY ignore TYPE A2X-PC5-QoS-Parameters PRESENCE optional }|
{ ID id-MobileIAB-Authorized CRITICALITY ignore TYPE MobileIAB-Authorized PRESENCE optional }|
{ ID id-NoPDUSessionIndication CRITICALITY ignore TYPE NoPDUSessionIndication PRESENCE optional }|
{ ID id-Partially-Allowed-NSSAI CRITICALITY ignore TYPE Partially-Allowed-NSSAI PRESENCE optional }|
{ ID id-SLPositioningRangingServiceInfo CRITICALITY ignore TYPE SLPositioningRangingServiceInfo PRESENCE optional },
...
}
-- **************************************************************
--
-- HANDOVER REQUEST ACKNOWLEDGE
--
-- **************************************************************
HandoverRequestAcknowledge ::= SEQUENCE {
protocolIEs ProtocolIE-Container { {HandoverRequestAcknowledgeIEs} },
...
}
HandoverRequestAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceAdmittedList CRITICALITY ignore TYPE PDUSessionResourceAdmittedList PRESENCE mandatory }|
{ ID id-PDUSessionResourceFailedToSetupListHOAck CRITICALITY ignore TYPE PDUSessionResourceFailedToSetupListHOAck PRESENCE optional }|
{ ID id-TargetToSource-TransparentContainer CRITICALITY reject TYPE TargetToSource-TransparentContainer PRESENCE mandatory }|
{ ID id-CriticalityDiagnostics CRITICALITY ignore TYPE CriticalityDiagnostics PRESENCE optional }|
{ ID id-NPN-AccessInformation CRITICALITY reject TYPE NPN-AccessInformation PRESENCE optional }|
{ ID id-RedCapIndication CRITICALITY ignore TYPE RedCapIndication PRESENCE optional }|
{ ID id-ERedCapIndication CRITICALITY ignore TYPE ERedCapIndication PRESENCE optional },
...
}
-- **************************************************************
--
-- HANDOVER FAILURE
--
-- **************************************************************
HandoverFailure ::= SEQUENCE {
protocolIEs ProtocolIE-Container { { HandoverFailureIEs} },
...
}
HandoverFailureIEs NGAP-PROTOCOL-IES ::= {
{ ID id-AMF-UE-NGAP-ID CRITICALITY ignore TYPE AMF-UE-NGAP-ID PRESENCE mandatory }|
{ ID id-Cause CRITICALITY ignore TYPE Cause PRESENCE mandatory }|
{ ID id-CriticalityDiagnostics CRITICALITY ignore TYPE CriticalityDiagnostics PRESENCE optional }|
{ ID id-TargettoSource-Failure-TransparentContainer CRITICALITY ignore TYPE TargettoSource-Failure-TransparentContainer PRESENCE optional },
...
}
-- **************************************************************
--
-- Handover Notification Elementary Procedure
--
-- **************************************************************
-- **************************************************************
--
-- HANDOVER NOTIFY
--
-- **************************************************************
HandoverNotify ::= SEQUENCE {
protocolIEs ProtocolIE-Container { { HandoverNotifyIEs} },
...
}
HandoverNotifyIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UserLocationInformation CRITICALITY ignore TYPE UserLocationInformation PRESENCE mandatory }|
{ ID id-NotifySourceNGRANNode CRITICALITY ignore TYPE NotifySourceNGRANNode PRESENCE optional },
...
}
-- **************************************************************
--
-- Path Switch Request Elementary Procedure
--
-- **************************************************************
-- **************************************************************
--
-- PATH SWITCH REQUEST
--
-- **************************************************************
PathSwitchRequest ::= SEQUENCE {
protocolIEs ProtocolIE-Container { { PathSwitchRequestIEs} },
...
}
PathSwitchRequestIEs NGAP-PROTOCOL-IES ::= {
{ ID id-RAN-UE-NGAP-ID CRITICALITY reject TYPE RAN-UE-NGAP-ID PRESENCE mandatory }|
{ ID id-SourceAMF-UE-NGAP-ID CRITICALITY reject TYPE AMF-UE-NGAP-ID PRESENCE mandatory }|
{ ID id-UserLocationInformation CRITICALITY ignore TYPE UserLocationInformation PRESENCE mandatory }|
{ ID id-UESecurityCapabilities CRITICALITY ignore TYPE UESecurityCapabilities PRESENCE mandatory }|
{ ID id-PDUSessionResourceToBeSwitchedDLList CRITICALITY reject TYPE PDUSessionResourceToBeSwitchedDLList PRESENCE mandatory }|
{ ID id-PDUSessionResourceFailedToSetupListPSReq CRITICALITY ignore TYPE PDUSessionResourceFailedToSetupListPSReq PRESENCE optional }|
{ ID id-RRC-Resume-Cause CRITICALITY ignore TYPE RRCEstablishmentCause PRESENCE optional }|
{ ID id-RedCapIndication CRITICALITY ignore TYPE RedCapIndication PRESENCE optional }|
{ ID id-ERedCapIndication CRITICALITY ignore TYPE ERedCapIndication PRESENCE optional },
...
}
-- **************************************************************
--
-- PATH SWITCH REQUEST ACKNOWLEDGE
--
-- **************************************************************
PathSwitchRequestAcknowledge ::= SEQUENCE {
protocolIEs ProtocolIE-Container { { PathSwitchRequestAcknowledgeIEs} },
...
}
PathSwitchRequestAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-UESecurityCapabilities CRITICALITY reject TYPE UESecurityCapabilities PRESENCE optional }|
{ ID id-SecurityContext CRITICALITY reject TYPE SecurityContext PRESENCE mandatory }|
{ ID id-NewSecurityContextInd CRITICALITY reject TYPE NewSecurityContextInd PRESENCE optional }|
{ ID id-PDUSessionResourceSwitchedList CRITICALITY ignore TYPE PDUSessionResourceSwitchedList PRESENCE mandatory }|
{ ID id-PDUSessionResourceReleasedListPSAck CRITICALITY ignore TYPE PDUSessionResourceReleasedListPSAck PRESENCE optional }|
{ ID id-AllowedNSSAI CRITICALITY reject TYPE AllowedNSSAI PRESENCE mandatory }|
{ ID id-CoreNetworkAssistanceInformationForInactive CRITICALITY ignore TYPE CoreNetworkAssistanceInformationForInactive PRESENCE optional }|
{ ID id-RRCInactiveTransitionReportRequest CRITICALITY ignore TYPE RRCInactiveTransitionReportRequest PRESENCE optional }|
{ ID id-CriticalityDiagnostics CRITICALITY ignore TYPE CriticalityDiagnostics PRESENCE optional }|
{ ID id-RedirectionVoiceFallback CRITICALITY ignore TYPE RedirectionVoiceFallback PRESENCE optional }|
{ ID id-CNAssistedRANTuning CRITICALITY ignore TYPE CNAssistedRANTuning PRESENCE optional }|
{ ID id-SRVCCOperationPossible CRITICALITY ignore TYPE SRVCCOperationPossible PRESENCE optional }|
{ ID id-Enhanced-CoverageRestriction CRITICALITY ignore TYPE Enhanced-CoverageRestriction PRESENCE optional }|
{ ID id-Extended-ConnectedTime CRITICALITY ignore TYPE Extended-ConnectedTime PRESENCE optional }|
{ ID id-UE-DifferentiationInfo CRITICALITY ignore TYPE UE-DifferentiationInfo PRESENCE optional }|
{ ID id-NRV2XServicesAuthorized CRITICALITY ignore TYPE NRV2XServicesAuthorized PRESENCE optional }|
{ ID id-LTEV2XServicesAuthorized CRITICALITY ignore TYPE LTEV2XServicesAuthorized PRESENCE optional }|
{ ID id-NRUESidelinkAggregateMaximumBitrate CRITICALITY ignore TYPE NRUESidelinkAggregateMaximumBitrate PRESENCE optional }|
{ ID id-LTEUESidelinkAggregateMaximumBitrate CRITICALITY ignore TYPE LTEUESidelinkAggregateMaximumBitrate PRESENCE optional }|
{ ID id-PC5QoSParameters CRITICALITY ignore TYPE PC5QoSParameters PRESENCE optional }|
{ ID id-CEmodeBrestricted CRITICALITY ignore TYPE CEmodeBrestricted PRESENCE optional }|
{ ID id-UE-UP-CIoT-Support CRITICALITY ignore TYPE UE-UP-CIoT-Support PRESENCE optional }|
{ ID id-UERadioCapabilityID CRITICALITY reject TYPE UERadioCapabilityID PRESENCE optional }|
{ ID id-ManagementBasedMDTPLMNList CRITICALITY ignore TYPE MDTPLMNList PRESENCE optional }|
{ ID id-TimeSyncAssistanceInfo CRITICALITY ignore TYPE TimeSyncAssistanceInfo PRESENCE optional }|
{ ID id-FiveG-ProSeAuthorized CRITICALITY ignore TYPE FiveG-ProSeAuthorized PRESENCE optional }|
{ ID id-FiveG-ProSeUEPC5AggregateMaximumBitRate CRITICALITY ignore TYPE NRUESidelinkAggregateMaximumBitrate PRESENCE optional }|
{ ID id-FiveG-ProSePC5QoSParameters CRITICALITY ignore TYPE FiveG-ProSePC5QoSParameters PRESENCE optional }|
{ ID id-ManagementBasedMDTPLMNModificationList CRITICALITY ignore TYPE MDTPLMNModificationList PRESENCE optional }|
{ ID id-IAB-Authorized CRITICALITY ignore TYPE IAB-Authorized PRESENCE optional }|
{ ID id-AerialUEsubscriptionInformation CRITICALITY ignore TYPE AerialUEsubscriptionInformation PRESENCE optional }|
{ ID id-NR-A2X-ServicesAuthorized CRITICALITY ignore TYPE NR-A2X-ServicesAuthorized PRESENCE optional }|
{ ID id-LTE-A2X-ServicesAuthorized CRITICALITY ignore TYPE LTE-A2X-ServicesAuthorized PRESENCE optional }|
{ ID id-NR-A2X-UE-PC5-AggregateMaximumBitRate CRITICALITY ignore TYPE NRUESidelinkAggregateMaximumBitrate PRESENCE optional }|
{ ID id-LTE-A2X-UE-PC5-AggregateMaximumBitRate CRITICALITY ignore TYPE LTEUESidelinkAggregateMaximumBitrate PRESENCE optional }|
{ ID id-A2X-PC5-QoS-Parameters CRITICALITY ignore TYPE A2X-PC5-QoS-Parameters PRESENCE optional }|
{ ID id-MobileIAB-Authorized CRITICALITY ignore TYPE MobileIAB-Authorized PRESENCE optional }|
{ ID id-Partially-Allowed-NSSAI CRITICALITY ignore TYPE Partially-Allowed-NSSAI PRESENCE optional }|
{ ID id-SLPositioningRangingServiceInfo CRITICALITY ignore TYPE SLPositioningRangingServiceInfo PRESENCE optional },
...
}
-- **************************************************************
--
-- PATH SWITCH REQUEST FAILURE
--
-- **************************************************************
PathSwitchRequestFailure ::= SEQUENCE {
protocolIEs ProtocolIE-Container { { PathSwitchRequestFailureIEs} },
...
}
PathSwitchRequestFailureIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceReleasedListPSFail CRITICALITY ignore TYPE PDUSessionResourceReleasedListPSFail PRESENCE mandatory }|
{ ID id-CriticalityDiagnostics CRITICALITY ignore TYPE CriticalityDiagnostics PRESENCE optional },
...
}
-- **************************************************************
--
-- Handover Cancellation Elementary Procedure
--
-- **************************************************************
-- **************************************************************
--
-- HANDOVER CANCEL
--
-- **************************************************************
HandoverCancel ::= SEQUENCE {
protocolIEs ProtocolIE-Container { { HandoverCancelIEs} },
...
}
HandoverCancelIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-Cause CRITICALITY ignore TYPE Cause PRESENCE mandatory },
...
}
-- **************************************************************
--
-- HANDOVER CANCEL ACKNOWLEDGE
--
-- **************************************************************
HandoverCancelAcknowledge ::= SEQUENCE {
protocolIEs ProtocolIE-Container { { HandoverCancelAcknowledgeIEs} },
...
}
HandoverCancelAcknowledgeIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-CriticalityDiagnostics CRITICALITY ignore TYPE CriticalityDiagnostics PRESENCE optional },
...
}
-- **************************************************************
--
-- HANDOVER SUCCESS ELEMENTARY PROCEDURE
--
-- **************************************************************
-- **************************************************************
--
-- HANDOVER SUCCESS
--
-- **************************************************************
HandoverSuccess ::= SEQUENCE {
protocolIEs ProtocolIE-Container { { HandoverSuccessIEs} },
...
}
HandoverSuccessIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory },
...
}
-- **************************************************************
--
-- UPLINK RAN EARLY STATUS TRANSFER ELEMENTARY PROCEDURE
--
-- **************************************************************
-- **************************************************************
--
-- Uplink RAN Early Status Transfer
--
-- **************************************************************
UplinkRANEarlyStatusTransfer ::= SEQUENCE {
protocolIEs ProtocolIE-Container { {UplinkRANEarlyStatusTransferIEs} },
...
}
UplinkRANEarlyStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-EarlyStatusTransfer-TransparentContainer CRITICALITY reject TYPE EarlyStatusTransfer-TransparentContainer PRESENCE mandatory },
...
}
-- **************************************************************
--
-- DOWNLINK RAN EARLY STATUS TRANSFER ELEMENTARY PROCEDURE
--
-- **************************************************************
-- **************************************************************
--
-- Downlink RAN Early Status Transfer
--
-- **************************************************************
DownlinkRANEarlyStatusTransfer ::= SEQUENCE {
protocolIEs ProtocolIE-Container { {DownlinkRANEarlyStatusTransferIEs} },
...
}
DownlinkRANEarlyStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-EarlyStatusTransfer-TransparentContainer CRITICALITY reject TYPE EarlyStatusTransfer-TransparentContainer PRESENCE mandatory },
...
}
-- **************************************************************
--
-- Uplink RAN Status Transfer Elementary Procedure
--
-- **************************************************************
-- **************************************************************
--
-- UPLINK RAN STATUS TRANSFER
--
-- **************************************************************
UplinkRANStatusTransfer ::= SEQUENCE {
protocolIEs ProtocolIE-Container { {UplinkRANStatusTransferIEs} },
...
}
UplinkRANStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANStatusTransfer-TransparentContainer CRITICALITY reject TYPE RANStatusTransfer-TransparentContainer PRESENCE mandatory },
...
}
-- **************************************************************
--
-- Downlink RAN Status Transfer Elementary Procedure
--
-- **************************************************************
-- **************************************************************
--
-- DOWNLINK RAN STATUS TRANSFER
--
-- **************************************************************
DownlinkRANStatusTransfer ::= SEQUENCE {
protocolIEs ProtocolIE-Container { {DownlinkRANStatusTransferIEs} },
...
}
DownlinkRANStatusTransferIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RANStatusTransfer-TransparentContainer CRITICALITY reject TYPE RANStatusTransfer-TransparentContainer PRESENCE mandatory },
...
}
-- **************************************************************
--
-- PAGING ELEMENTARY PROCEDURE
--
-- **************************************************************
-- **************************************************************
--
-- PAGING
--
-- **************************************************************
Paging ::= SEQUENCE {
protocolIEs ProtocolIE-Container { {PagingIEs} },
...
}
PagingIEs NGAP-PROTOCOL-IES ::= {
{ ID id-UEPagingIdentity CRITICALITY ignore TYPE UEPagingIdentity PRESENCE mandatory }|
{ ID id-PagingDRX CRITICALITY ignore TYPE PagingDRX PRESENCE optional }|
{ ID id-TAIListForPaging CRITICALITY ignore TYPE TAIListForPaging PRESENCE mandatory }|
{ ID id-PagingPriority CRITICALITY ignore TYPE PagingPriority PRESENCE optional }|
{ ID id-UERadioCapabilityForPaging CRITICALITY ignore TYPE UERadioCapabilityForPaging PRESENCE optional }|
{ ID id-PagingOrigin CRITICALITY ignore TYPE PagingOrigin PRESENCE optional }|
{ ID id-AssistanceDataForPaging CRITICALITY ignore TYPE AssistanceDataForPaging PRESENCE optional }|
{ ID id-NB-IoT-Paging-eDRXInfo CRITICALITY ignore TYPE NB-IoT-Paging-eDRXInfo PRESENCE optional }|
{ ID id-NB-IoT-PagingDRX CRITICALITY ignore TYPE NB-IoT-PagingDRX PRESENCE optional }|
{ ID id-Enhanced-CoverageRestriction CRITICALITY ignore TYPE Enhanced-CoverageRestriction PRESENCE optional }|
{ ID id-WUS-Assistance-Information CRITICALITY ignore TYPE WUS-Assistance-Information PRESENCE optional }|
{ ID id-EUTRA-PagingeDRXInformation CRITICALITY ignore TYPE EUTRA-PagingeDRXInformation PRESENCE optional }|
{ ID id-CEmodeBrestricted CRITICALITY ignore TYPE CEmodeBrestricted PRESENCE optional }|
{ ID id-NR-PagingeDRXInformation CRITICALITY ignore TYPE NR-PagingeDRXInformation PRESENCE optional }|
{ ID id-PagingCause CRITICALITY ignore TYPE PagingCause PRESENCE optional }|
{ ID id-PEIPSassistanceInformation CRITICALITY ignore TYPE PEIPSassistanceInformation PRESENCE optional },
...
}
-- **************************************************************
--
-- NAS TRANSPORT ELEMENTARY PROCEDURES
--
-- **************************************************************
-- **************************************************************
--
-- INITIAL UE MESSAGE
--
-- **************************************************************
InitialUEMessage ::= SEQUENCE {
protocolIEs ProtocolIE-Container { {InitialUEMessage-IEs} },
...
}
InitialUEMessage-IEs NGAP-PROTOCOL-IES ::= {
{ ID id-RAN-UE-NGAP-ID CRITICALITY reject TYPE RAN-UE-NGAP-ID PRESENCE mandatory }|
{ ID id-NAS-PDU CRITICALITY reject TYPE NAS-PDU PRESENCE mandatory }|
{ ID id-UserLocationInformation CRITICALITY reject TYPE UserLocationInformation PRESENCE mandatory }|
{ ID id-RRCEstablishmentCause CRITICALITY ignore TYPE RRCEstablishmentCause PRESENCE mandatory }|
{ ID id-FiveG-S-TMSI CRITICALITY reject TYPE FiveG-S-TMSI PRESENCE optional }|
{ ID id-AMFSetID CRITICALITY ignore TYPE AMFSetID PRESENCE optional }|
{ ID id-UEContextRequest CRITICALITY ignore TYPE UEContextRequest PRESENCE optional }|
{ ID id-AllowedNSSAI CRITICALITY reject TYPE AllowedNSSAI PRESENCE optional }|
{ ID id-SourceToTarget-AMFInformationReroute CRITICALITY ignore TYPE SourceToTarget-AMFInformationReroute PRESENCE optional }|
{ ID id-SelectedPLMNIdentity CRITICALITY ignore TYPE PLMNIdentity PRESENCE optional }|
{ ID id-IABNodeIndication CRITICALITY reject TYPE IABNodeIndication PRESENCE optional }|
{ ID id-CEmodeBSupport-Indicator CRITICALITY reject TYPE CEmodeBSupport-Indicator PRESENCE optional }|
{ ID id-LTEM-Indication CRITICALITY ignore TYPE LTEM-Indication PRESENCE optional }|
{ ID id-EDT-Session CRITICALITY ignore TYPE EDT-Session PRESENCE optional }|
{ ID id-AuthenticatedIndication CRITICALITY ignore TYPE AuthenticatedIndication PRESENCE optional }|
{ ID id-NPN-AccessInformation CRITICALITY reject TYPE NPN-AccessInformation PRESENCE optional }|
{ ID id-RedCapIndication CRITICALITY ignore TYPE RedCapIndication PRESENCE optional }|
{ ID id-SelectedNID CRITICALITY ignore TYPE NID PRESENCE optional }|
{ ID id-MobileIABNodeIndication CRITICALITY reject TYPE MobileIABNodeIndication PRESENCE optional }|
{ ID id-Partially-Allowed-NSSAI CRITICALITY ignore TYPE Partially-Allowed-NSSAI PRESENCE optional }|
{ ID id-ERedCapIndication CRITICALITY ignore TYPE ERedCapIndication PRESENCE optional }|
{ ID id-AUN3DeviceAccessInfo CRITICALITY ignore TYPE AUN3DeviceAccessInfo PRESENCE optional },
...
}
-- **************************************************************
--
-- DOWNLINK NAS TRANSPORT
--
-- **************************************************************
DownlinkNASTransport ::= SEQUENCE {
protocolIEs ProtocolIE-Container { {DownlinkNASTransport-IEs} },
...
}
DownlinkNASTransport-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-OldAMF CRITICALITY reject TYPE AMFName PRESENCE optional }|
{ ID id-RANPagingPriority CRITICALITY ignore TYPE RANPagingPriority PRESENCE optional }|
{ ID id-NAS-PDU CRITICALITY reject TYPE NAS-PDU PRESENCE mandatory }|
{ ID id-MobilityRestrictionList CRITICALITY ignore TYPE MobilityRestrictionList PRESENCE optional }|
{ ID id-IndexToRFSP CRITICALITY ignore TYPE IndexToRFSP PRESENCE optional }|
{ ID id-UEAggregateMaximumBitRate CRITICALITY ignore TYPE UEAggregateMaximumBitRate PRESENCE optional }|
{ ID id-AllowedNSSAI CRITICALITY reject TYPE AllowedNSSAI PRESENCE optional }|
{ ID id-SRVCCOperationPossible CRITICALITY ignore TYPE SRVCCOperationPossible PRESENCE optional }|
{ ID id-Enhanced-CoverageRestriction CRITICALITY ignore TYPE Enhanced-CoverageRestriction PRESENCE optional }|
{ ID id-Extended-ConnectedTime CRITICALITY ignore TYPE Extended-ConnectedTime PRESENCE optional }|
{ ID id-UE-DifferentiationInfo CRITICALITY ignore TYPE UE-DifferentiationInfo PRESENCE optional }|
{ ID id-CEmodeBrestricted CRITICALITY ignore TYPE CEmodeBrestricted PRESENCE optional }|
{ ID id-UERadioCapability CRITICALITY ignore TYPE UERadioCapability PRESENCE optional }|
{ ID id-UECapabilityInfoRequest CRITICALITY ignore TYPE UECapabilityInfoRequest PRESENCE optional }|
{ ID id-EndIndication CRITICALITY ignore TYPE EndIndication PRESENCE optional }|
{ ID id-UERadioCapabilityID CRITICALITY reject TYPE UERadioCapabilityID PRESENCE optional }|
{ ID id-TargetNSSAIInformation CRITICALITY ignore TYPE TargetNSSAIInformation PRESENCE optional }|
{ ID id-MaskedIMEISV CRITICALITY ignore TYPE MaskedIMEISV PRESENCE optional }|
{ ID id-Partially-Allowed-NSSAI CRITICALITY ignore TYPE Partially-Allowed-NSSAI PRESENCE optional }|
{ ID id-MobileIAB-Authorized CRITICALITY ignore TYPE MobileIAB-Authorized PRESENCE optional }|
{ ID id-ExtendedOldAMF CRITICALITY ignore TYPE Extended-AMFName PRESENCE optional },
...
}
-- **************************************************************
--
-- UPLINK NAS TRANSPORT
--
-- **************************************************************
UplinkNASTransport ::= SEQUENCE {
protocolIEs ProtocolIE-Container { {UplinkNASTransport-IEs} },
...
}
UplinkNASTransport-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NAS-PDU CRITICALITY reject TYPE NAS-PDU PRESENCE mandatory }|
{ ID id-UserLocationInformation CRITICALITY ignore TYPE UserLocationInformation PRESENCE mandatory }|
{ ID id-W-AGFIdentityInformation CRITICALITY reject TYPE OCTET STRING PRESENCE optional }|
{ ID id-TNGFIdentityInformation CRITICALITY reject TYPE OCTET STRING PRESENCE optional }|
{ ID id-TWIFIdentityInformation CRITICALITY reject TYPE OCTET STRING PRESENCE optional },
...
}
-- **************************************************************
--
-- NAS NON DELIVERY INDICATION
--
-- **************************************************************
NASNonDeliveryIndication ::= SEQUENCE {
protocolIEs ProtocolIE-Container { {NASNonDeliveryIndication-IEs} },
...
}
NASNonDeliveryIndication-IEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NAS-PDU CRITICALITY ignore TYPE NAS-PDU PRESENCE mandatory }|
{ ID id-Cause CRITICALITY ignore TYPE Cause PRESENCE mandatory },
...
}
-- **************************************************************
--
-- REROUTE NAS REQUEST
--
-- **************************************************************
RerouteNASRequest ::= SEQUENCE {
protocolIEs ProtocolIE-Container { {RerouteNASRequest-IEs} },
...
}
RerouteNASRequest-IEs NGAP-PROTOCOL-IES ::= {
{ ID id-RAN-UE-NGAP-ID CRITICALITY reject TYPE RAN-UE-NGAP-ID PRESENCE mandatory }|
{ ID id-AMF-UE-NGAP-ID CRITICALITY ignore TYPE AMF-UE-NGAP-ID PRESENCE optional }|
{ ID id-NGAP-Message CRITICALITY reject TYPE OCTET STRING PRESENCE mandatory }|
{ ID id-AMFSetID CRITICALITY reject TYPE AMFSetID PRESENCE mandatory }|
{ ID id-AllowedNSSAI CRITICALITY reject TYPE AllowedNSSAI PRESENCE optional }|
{ ID id-SourceToTarget-AMFInformationReroute CRITICALITY ignore TYPE SourceToTarget-AMFInformationReroute PRESENCE optional }|
{ ID id-Partially-Allowed-NSSAI CRITICALITY ignore TYPE Partially-Allowed-NSSAI PRESENCE optional },
...
}
-- **************************************************************
--
-- INTERFACE MANAGEMENT ELEMENTARY PROCEDURES
--
-- **************************************************************
-- **************************************************************
--
-- NG Setup Elementary Procedure
--
-- **************************************************************
-- **************************************************************
--
-- NG SETUP REQUEST
--
-- **************************************************************
NGSetupRequest ::= SEQUENCE {
protocolIEs ProtocolIE-Container { {NGSetupRequestIEs} },
...
}
NGSetupRequestIEs NGAP-PROTOCOL-IES ::= {
{ ID id-GlobalRANNodeID CRITICALITY reject TYPE GlobalRANNodeID PRESENCE mandatory }|
{ ID id-RANNodeName CRITICALITY ignore TYPE RANNodeName PRESENCE optional }|
{ ID id-SupportedTAList CRITICALITY reject TYPE SupportedTAList PRESENCE mandatory }|
{ ID id-DefaultPagingDRX CRITICALITY ignore TYPE PagingDRX PRESENCE mandatory }|
{ ID id-UERetentionInformation CRITICALITY ignore TYPE UERetentionInformation PRESENCE optional }|
{ ID id-NB-IoT-DefaultPagingDRX CRITICALITY ignore TYPE NB-IoT-DefaultPagingDRX PRESENCE optional }|
{ ID id-Extended-RANNodeName CRITICALITY ignore TYPE Extended-RANNodeName PRESENCE optional },
...
}
-- **************************************************************
--
-- NG SETUP RESPONSE
--
-- **************************************************************
NGSetupResponse ::= SEQUENCE {
protocolIEs ProtocolIE-Container { {NGSetupResponseIEs} },
...
}
NGSetupResponseIEs NGAP-PROTOCOL-IES ::= {
{ ID id-AMFName CRITICALITY reject TYPE AMFName PRESENCE mandatory }|
{ ID id-ServedGUAMIList CRITICALITY reject TYPE ServedGUAMIList PRESENCE mandatory }|
{ ID id-RelativeAMFCapacity CRITICALITY ignore TYPE RelativeAMFCapacity PRESENCE mandatory }|
{ ID id-PLMNSupportList CRITICALITY reject TYPE PLMNSupportList PRESENCE mandatory }|
{ ID id-CriticalityDiagnostics CRITICALITY ignore TYPE CriticalityDiagnostics PRESENCE optional }|
{ ID id-UERetentionInformation CRITICALITY ignore TYPE UERetentionInformation PRESENCE optional }|
{ ID id-IAB-Supported CRITICALITY ignore TYPE IAB-Supported PRESENCE optional }|
{ ID id-Extended-AMFName CRITICALITY ignore TYPE Extended-AMFName PRESENCE optional }|
{ ID id-MobileIAB-Supported CRITICALITY ignore TYPE MobileIAB-Supported PRESENCE optional },
...
}
-- **************************************************************
--
-- NG SETUP FAILURE
--
-- **************************************************************
NGSetupFailure ::= SEQUENCE {
protocolIEs ProtocolIE-Container { {NGSetupFailureIEs} },
...
}
NGSetupFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- RAN Configuration Update Elementary Procedure
--
-- **************************************************************
-- **************************************************************
--
-- RAN CONFIGURATION UPDATE
--
-- **************************************************************
RANConfigurationUpdate ::= SEQUENCE {
protocolIEs ProtocolIE-Container { {RANConfigurationUpdateIEs} },
...
}
RANConfigurationUpdateIEs NGAP-PROTOCOL-IES ::= {
{ ID id-RANNodeName CRITICALITY ignore TYPE RANNodeName PRESENCE optional }|
{ ID id-SupportedTAList CRITICALITY reject TYPE SupportedTAList PRESENCE optional }|
{ ID id-DefaultPagingDRX CRITICALITY ignore TYPE PagingDRX PRESENCE optional }|
{ ID id-GlobalRANNodeID CRITICALITY ignore TYPE GlobalRANNodeID PRESENCE optional }|
{ ID id-NGRAN-TNLAssociationToRemoveList CRITICALITY reject TYPE NGRAN-TNLAssociationToRemoveList PRESENCE optional }|
{ ID id-NB-IoT-DefaultPagingDRX CRITICALITY ignore TYPE NB-IoT-DefaultPagingDRX PRESENCE optional }|
{ ID id-Extended-RANNodeName CRITICALITY ignore TYPE Extended-RANNodeName PRESENCE optional },
...
}
-- **************************************************************
--
-- RAN CONFIGURATION UPDATE ACKNOWLEDGE
--
-- **************************************************************
RANConfigurationUpdateAcknowledge ::= SEQUENCE {
protocolIEs ProtocolIE-Container { {RANConfigurationUpdateAcknowledgeIEs} },
...
}
RANConfigurationUpdateAcknowledgeIEs NGAP-PROTOCOL-IES ::= {
{ ID id-CriticalityDiagnostics CRITICALITY ignore TYPE CriticalityDiagnostics PRESENCE optional },
...
}
-- **************************************************************
--
-- RAN CONFIGURATION UPDATE FAILURE
--
-- **************************************************************
RANConfigurationUpdateFailure ::= SEQUENCE {
protocolIEs ProtocolIE-Container { {RANConfigurationUpdateFailureIEs} },
...
}
RANConfigurationUpdateFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- AMF Configuration Update Elementary Procedure
--
-- **************************************************************
-- **************************************************************
--
-- AMF CONFIGURATION UPDATE
--
-- **************************************************************
AMFConfigurationUpdate ::= SEQUENCE {
protocolIEs ProtocolIE-Container { {AMFConfigurationUpdateIEs} },
...
}
AMFConfigurationUpdateIEs NGAP-PROTOCOL-IES ::= {
{ ID id-AMFName CRITICALITY reject TYPE AMFName PRESENCE optional }|
{ ID id-ServedGUAMIList CRITICALITY reject TYPE ServedGUAMIList PRESENCE optional }|
{ ID id-RelativeAMFCapacity CRITICALITY ignore TYPE RelativeAMFCapacity PRESENCE optional }|
{ ID id-PLMNSupportList CRITICALITY reject TYPE PLMNSupportList PRESENCE optional }|
{ ID id-AMF-TNLAssociationToAddList CRITICALITY ignore TYPE AMF-TNLAssociationToAddList PRESENCE optional }|
{ ID id-AMF-TNLAssociationToRemoveList CRITICALITY ignore TYPE AMF-TNLAssociationToRemoveList PRESENCE optional }|
{ ID id-AMF-TNLAssociationToUpdateList CRITICALITY ignore TYPE AMF-TNLAssociationToUpdateList PRESENCE optional }|
{ ID id-Extended-AMFName CRITICALITY ignore TYPE Extended-AMFName PRESENCE optional },
...
}
-- **************************************************************
--
-- AMF CONFIGURATION UPDATE ACKNOWLEDGE
--
-- **************************************************************
AMFConfigurationUpdateAcknowledge ::= SEQUENCE {
protocolIEs ProtocolIE-Container { {AMFConfigurationUpdateAcknowledgeIEs} },
...
}
AMFConfigurationUpdateAcknowledgeIEs NGAP-PROTOCOL-IES ::= {
{ ID id-AMF-TNLAssociationSetupList CRITICALITY ignore TYPE AMF-TNLAssociationSetupList PRESENCE optional }|
{ ID id-AMF-TNLAssociationFailedToSetupList CRITICALITY ignore TYPE TNLAssociationList PRESENCE optional }|
{ ID id-CriticalityDiagnostics CRITICALITY ignore TYPE CriticalityDiagnostics PRESENCE optional },
...
}
-- **************************************************************
--
-- AMF CONFIGURATION UPDATE FAILURE
--
-- **************************************************************
AMFConfigurationUpdateFailure ::= SEQUENCE {
protocolIEs ProtocolIE-Container { {AMFConfigurationUpdateFailureIEs} },
...
}
AMFConfigurationUpdateFailureIEs NGAP-PROTOCOL-IES ::= {
{ ID id-Cause CRITICALITY ignore TYPE Cause PRESENCE mandatory }|
{ ID id-TimeToWait CRITICALITY ignore TYPE TimeToWait PRESENCE optional }|
{ ID id-CriticalityDiagnostics CRITICALITY ignore TYPE CriticalityDiagnostics PRESENCE optional },
...
}
-- **************************************************************
--
-- AMF Status Indication Elementary Procedure
--
-- **************************************************************
-- **************************************************************
--
-- AMF STATUS INDICATION
--
-- **************************************************************
AMFStatusIndication ::= SEQUENCE {
protocolIEs ProtocolIE-Container { {AMFStatusIndicationIEs} },
...
}
AMFStatusIndicationIEs NGAP-PROTOCOL-IES ::= {
{ ID id-UnavailableGUAMIList CRITICALITY reject TYPE UnavailableGUAMIList PRESENCE mandatory },
...
}
-- **************************************************************
--
-- NG Reset Elementary Procedure
--
-- **************************************************************
-- **************************************************************
--
-- NG RESET
--
-- **************************************************************
NGReset ::= SEQUENCE {
protocolIEs ProtocolIE-Container { {NGResetIEs} },
...
}
NGResetIEs NGAP-PROTOCOL-IES ::= {
{ ID id-Cause CRITICALITY ignore TYPE Cause PRESENCE mandatory }|
{ ID id-ResetType CRITICALITY reject TYPE ResetType PRESENCE mandatory },
...
}
-- **************************************************************
--
-- NG RESET ACKNOWLEDGE
--
-- **************************************************************
NGResetAcknowledge ::= SEQUENCE {
protocolIEs ProtocolIE-Container { {NGResetAcknowledgeIEs} },
...
}
NGResetAcknowledgeIEs NGAP-PROTOCOL-IES ::= {
{ ID id-UE-associatedLogicalNG-connectionList CRITICALITY ignore TYPE UE-associatedLogicalNG-connectionList PRESENCE optional }|
{ ID id-CriticalityDiagnostics CRITICALITY ignore TYPE CriticalityDiagnostics PRESENCE optional },
...
}
-- **************************************************************
--
-- Error Indication Elementary Procedure
--
-- **************************************************************
-- **************************************************************
--
-- ERROR INDICATION
--
-- **************************************************************
ErrorIndication ::= SEQUENCE {
protocolIEs ProtocolIE-Container { {ErrorIndicationIEs} },
...
}
ErrorIndicationIEs NGAP-PROTOCOL-IES ::= {
{ ID id-AMF-UE-NGAP-ID CRITICALITY ignore TYPE AMF-UE-NGAP-ID PRESENCE optional }|
{ ID id-RAN-UE-NGAP-ID CRITICALITY ignore TYPE RAN-UE-NGAP-ID PRESENCE optional }|
{ ID id-Cause CRITICALITY ignore TYPE Cause PRESENCE optional }|
{ ID id-CriticalityDiagnostics CRITICALITY ignore TYPE CriticalityDiagnostics PRESENCE optional }|
{ ID id-FiveG-S-TMSI CRITICALITY ignore TYPE FiveG-S-TMSI PRESENCE optional },
...
}
-- **************************************************************
--
-- OVERLOAD START
--
-- **************************************************************
OverloadStart ::= SEQUENCE {
protocolIEs ProtocolIE-Container { {OverloadStartIEs} },
...
}
OverloadStartIEs NGAP-PROTOCOL-IES ::= {
{ ID id-AMFOverloadResponse CRITICALITY reject TYPE OverloadResponse PRESENCE optional }|
{ ID id-AMFTrafficLoadReductionIndication CRITICALITY ignore TYPE TrafficLoadReductionIndication PRESENCE optional }|
{ ID id-OverloadStartNSSAIList CRITICALITY ignore TYPE OverloadStartNSSAIList PRESENCE optional },
...
}
-- **************************************************************
--
-- OVERLOAD STOP
--
-- **************************************************************
OverloadStop ::= SEQUENCE {
protocolIEs ProtocolIE-Container { {OverloadStopIEs} },
...
}
OverloadStopIEs NGAP-PROTOCOL-IES ::= {
...
}
-- **************************************************************
--
-- CONFIGURATION TRANSFER ELEMENTARY PROCEDURES
--
-- **************************************************************
-- **************************************************************
--
-- UPLINK RAN CONFIGURATION TRANSFER
--
-- **************************************************************
UplinkRANConfigurationTransfer ::= SEQUENCE {
protocolIEs ProtocolIE-Container { {UplinkRANConfigurationTransferIEs} },
...
}
UplinkRANConfigurationTransferIEs NGAP-PROTOCOL-IES ::= {
{ ID id-SONConfigurationTransferUL CRITICALITY ignore TYPE SONConfigurationTransfer PRESENCE optional }|
{ ID id-ENDC-SONConfigurationTransferUL CRITICALITY ignore TYPE EN-DCSONConfigurationTransfer PRESENCE optional }|
{ ID id-IntersystemSONConfigurationTransferUL CRITICALITY ignore TYPE IntersystemSONConfigurationTransfer PRESENCE optional },
...
}
-- **************************************************************
--
-- DOWNLINK RAN CONFIGURATION TRANSFER
--
-- **************************************************************
DownlinkRANConfigurationTransfer ::= SEQUENCE {
protocolIEs ProtocolIE-Container { {DownlinkRANConfigurationTransferIEs} },
...
}
DownlinkRANConfigurationTransferIEs NGAP-PROTOCOL-IES ::= {
{ ID id-SONConfigurationTransferDL CRITICALITY ignore TYPE SONConfigurationTransfer PRESENCE optional }|
{ ID id-ENDC-SONConfigurationTransferDL CRITICALITY ignore TYPE EN-DCSONConfigurationTransfer PRESENCE optional }|
{ ID id-IntersystemSONConfigurationTransferDL CRITICALITY ignore TYPE IntersystemSONConfigurationTransfer PRESENCE optional },
...
}
-- **************************************************************
--
-- WARNING MESSAGE TRANSMISSION ELEMENTARY PROCEDURES
--
-- **************************************************************
-- **************************************************************
--
-- Write-Replace Warning Elementary Procedure
--
-- **************************************************************
-- **************************************************************
--
-- WRITE-REPLACE WARNING REQUEST
--
-- **************************************************************
WriteReplaceWarningRequest ::= SEQUENCE {
protocolIEs ProtocolIE-Container { {WriteReplaceWarningRequestIEs} },
...
}
WriteReplaceWarningRequestIEs NGAP-PROTOCOL-IES ::= {
{ ID id-MessageIdentifier CRITICALITY reject TYPE MessageIdentifier PRESENCE mandatory }|
{ ID id-SerialNumber CRITICALITY reject TYPE SerialNumber PRESENCE mandatory }|
{ ID id-WarningAreaList CRITICALITY ignore TYPE WarningAreaList PRESENCE optional }|
{ ID id-RepetitionPeriod CRITICALITY reject TYPE RepetitionPeriod PRESENCE mandatory }|
{ ID id-NumberOfBroadcastsRequested CRITICALITY reject TYPE NumberOfBroadcastsRequested PRESENCE mandatory }|
{ ID id-WarningType CRITICALITY ignore TYPE WarningType PRESENCE optional }|
{ ID id-WarningSecurityInfo CRITICALITY ignore TYPE WarningSecurityInfo PRESENCE optional }|
{ ID id-DataCodingScheme CRITICALITY ignore TYPE DataCodingScheme PRESENCE optional }|
{ ID id-WarningMessageContents CRITICALITY ignore TYPE WarningMessageContents PRESENCE optional }|
{ ID id-ConcurrentWarningMessageInd CRITICALITY reject TYPE ConcurrentWarningMessageInd PRESENCE optional }|
{ ID id-WarningAreaCoordinates CRITICALITY ignore TYPE WarningAreaCoordinates PRESENCE optional },
...
}
-- **************************************************************
--
-- WRITE-REPLACE WARNING RESPONSE
--
-- **************************************************************
WriteReplaceWarningResponse ::= SEQUENCE {
protocolIEs ProtocolIE-Container { {WriteReplaceWarningResponseIEs} },
...
}
WriteReplaceWarningResponseIEs NGAP-PROTOCOL-IES ::= {
{ ID id-MessageIdentifier CRITICALITY reject TYPE MessageIdentifier PRESENCE mandatory }|
{ ID id-SerialNumber CRITICALITY reject TYPE SerialNumber PRESENCE mandatory }|
{ ID id-BroadcastCompletedAreaList CRITICALITY ignore TYPE BroadcastCompletedAreaList PRESENCE optional }|
{ ID id-CriticalityDiagnostics CRITICALITY ignore TYPE CriticalityDiagnostics PRESENCE optional },
...
}
-- **************************************************************
--
-- PWS Cancel Elementary Procedure
--
-- **************************************************************
-- **************************************************************
--
-- PWS CANCEL REQUEST
--
-- **************************************************************
PWSCancelRequest ::= SEQUENCE {
protocolIEs ProtocolIE-Container { {PWSCancelRequestIEs} },
...
}
PWSCancelRequestIEs NGAP-PROTOCOL-IES ::= {
{ ID id-MessageIdentifier CRITICALITY reject TYPE MessageIdentifier PRESENCE mandatory }|
{ ID id-SerialNumber CRITICALITY reject TYPE SerialNumber PRESENCE mandatory }|
{ ID id-WarningAreaList CRITICALITY ignore TYPE WarningAreaList PRESENCE optional }|
{ ID id-CancelAllWarningMessages CRITICALITY reject TYPE CancelAllWarningMessages PRESENCE optional },
...
}
-- **************************************************************
--
-- PWS CANCEL RESPONSE
--
-- **************************************************************
PWSCancelResponse ::= SEQUENCE {
protocolIEs ProtocolIE-Container { {PWSCancelResponseIEs} },
...
}
PWSCancelResponseIEs NGAP-PROTOCOL-IES ::= {
{ ID id-MessageIdentifier CRITICALITY reject TYPE MessageIdentifier PRESENCE mandatory }|
{ ID id-SerialNumber CRITICALITY reject TYPE SerialNumber PRESENCE mandatory }|
{ ID id-BroadcastCancelledAreaList CRITICALITY ignore TYPE BroadcastCancelledAreaList PRESENCE optional }|
{ ID id-CriticalityDiagnostics CRITICALITY ignore TYPE CriticalityDiagnostics PRESENCE optional },
...
}
-- **************************************************************
--
-- PWS Restart Indication Elementary Procedure
--
-- **************************************************************
-- **************************************************************
--
-- PWS RESTART INDICATION
--
-- **************************************************************
PWSRestartIndication ::= SEQUENCE {
protocolIEs ProtocolIE-Container { {PWSRestartIndicationIEs} },
...
}
PWSRestartIndicationIEs NGAP-PROTOCOL-IES ::= {
{ ID id-CellIDListForRestart CRITICALITY reject TYPE CellIDListForRestart PRESENCE mandatory }|
{ ID id-GlobalRANNodeID CRITICALITY reject TYPE GlobalRANNodeID PRESENCE mandatory }|
{ ID id-TAIListForRestart CRITICALITY reject TYPE TAIListForRestart PRESENCE mandatory }|
{ ID id-EmergencyAreaIDListForRestart CRITICALITY reject TYPE EmergencyAreaIDListForRestart PRESENCE optional },
...
}
-- **************************************************************
--
-- PWS Failure Indication Elementary Procedure
--
-- **************************************************************
-- **************************************************************
--
-- PWS FAILURE INDICATION
--
-- **************************************************************
PWSFailureIndication ::= SEQUENCE {
protocolIEs ProtocolIE-Container { {PWSFailureIndicationIEs} },
...
}
PWSFailureIndicationIEs NGAP-PROTOCOL-IES ::= {
{ ID id-PWSFailedCellIDList CRITICALITY reject TYPE PWSFailedCellIDList PRESENCE mandatory }|
{ ID id-GlobalRANNodeID CRITICALITY reject TYPE GlobalRANNodeID PRESENCE mandatory },
...
}
-- **************************************************************
--
-- NRPPA TRANSPORT ELEMENTARY PROCEDURES
--
-- **************************************************************
-- **************************************************************
--
-- DOWNLINK UE ASSOCIATED NRPPA TRANSPORT
--
-- **************************************************************
DownlinkUEAssociatedNRPPaTransport ::= SEQUENCE {
protocolIEs ProtocolIE-Container { {DownlinkUEAssociatedNRPPaTransportIEs} },
...
}
DownlinkUEAssociatedNRPPaTransportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RoutingID CRITICALITY reject TYPE RoutingID PRESENCE mandatory }|
{ ID id-NRPPa-PDU CRITICALITY reject TYPE NRPPa-PDU PRESENCE mandatory },
...
}
-- **************************************************************
--
-- UPLINK UE ASSOCIATED NRPPA TRANSPORT
--
-- **************************************************************
UplinkUEAssociatedNRPPaTransport ::= SEQUENCE {
protocolIEs ProtocolIE-Container { {UplinkUEAssociatedNRPPaTransportIEs} },
...
}
UplinkUEAssociatedNRPPaTransportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-RoutingID CRITICALITY reject TYPE RoutingID PRESENCE mandatory }|
{ ID id-NRPPa-PDU CRITICALITY reject TYPE NRPPa-PDU PRESENCE mandatory },
...
}
-- **************************************************************
--
-- DOWNLINK NON UE ASSOCIATED NRPPA TRANSPORT
--
-- **************************************************************
DownlinkNonUEAssociatedNRPPaTransport ::= SEQUENCE {
protocolIEs ProtocolIE-Container { {DownlinkNonUEAssociatedNRPPaTransportIEs} },
...
}
DownlinkNonUEAssociatedNRPPaTransportIEs NGAP-PROTOCOL-IES ::= {
{ ID id-RoutingID CRITICALITY reject TYPE RoutingID PRESENCE mandatory }|
{ ID id-NRPPa-PDU CRITICALITY reject TYPE NRPPa-PDU PRESENCE mandatory },
...
}
-- **************************************************************
--
-- UPLINK NON UE ASSOCIATED NRPPA TRANSPORT
--
-- **************************************************************
UplinkNonUEAssociatedNRPPaTransport ::= SEQUENCE {
protocolIEs ProtocolIE-Container { {UplinkNonUEAssociatedNRPPaTransportIEs} },
...
}
UplinkNonUEAssociatedNRPPaTransportIEs NGAP-PROTOCOL-IES ::= {
{ ID id-RoutingID CRITICALITY reject TYPE RoutingID PRESENCE mandatory }|
{ ID id-NRPPa-PDU CRITICALITY reject TYPE NRPPa-PDU PRESENCE mandatory },
...
}
-- **************************************************************
--
-- TRACE ELEMENTARY PROCEDURES
--
-- **************************************************************
-- **************************************************************
--
-- TRACE START
--
-- **************************************************************
TraceStart ::= SEQUENCE {
protocolIEs ProtocolIE-Container { {TraceStartIEs} },
...
}
TraceStartIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-TraceActivation CRITICALITY ignore TYPE TraceActivation PRESENCE mandatory },
...
}
-- **************************************************************
--
-- TRACE FAILURE INDICATION
--
-- **************************************************************
TraceFailureIndication ::= SEQUENCE {
protocolIEs ProtocolIE-Container { {TraceFailureIndicationIEs} },
...
}
TraceFailureIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NGRANTraceID CRITICALITY ignore TYPE NGRANTraceID PRESENCE mandatory }|
{ ID id-Cause CRITICALITY ignore TYPE Cause PRESENCE mandatory },
...
}
-- **************************************************************
--
-- DEACTIVATE TRACE
--
-- **************************************************************
DeactivateTrace ::= SEQUENCE {
protocolIEs ProtocolIE-Container { {DeactivateTraceIEs} },
...
}
DeactivateTraceIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-NGRANTraceID CRITICALITY ignore TYPE NGRANTraceID PRESENCE mandatory },
...
}
-- **************************************************************
--
-- CELL TRAFFIC TRACE
--
-- **************************************************************
CellTrafficTrace ::= SEQUENCE {
protocolIEs ProtocolIE-Container { {CellTrafficTraceIEs} },
...
}
CellTrafficTraceIEs NGAP-PROTOCOL-IES ::= {
{ID id-AMF-UE-NGAP-ID CRITICALITY reject TYPE AMF-UE-NGAP-ID PRESENCE mandatory }|
{ID id-RAN-UE-NGAP-ID CRITICALITY reject TYPE RAN-UE-NGAP-ID PRESENCE mandatory }|
{ID id-NGRANTraceID CRITICALITY ignore TYPE NGRANTraceID PRESENCE mandatory }|
{ID id-NGRAN-CGI CRITICALITY ignore TYPE NGRAN-CGI PRESENCE mandatory }|
{ID id-TraceCollectionEntityIPAddress CRITICALITY ignore TYPE TransportLayerAddress PRESENCE mandatory }|
{ID id-PrivacyIndicator CRITICALITY ignore TYPE PrivacyIndicator PRESENCE optional }|
{ID id-TraceCollectionEntityURI CRITICALITY ignore TYPE URI-address PRESENCE optional },
...
}
-- **************************************************************
--
-- LOCATION REPORTING ELEMENTARY PROCEDURES
--
-- **************************************************************
-- **************************************************************
--
-- LOCATION REPORTING CONTROL
--
-- **************************************************************
LocationReportingControl ::= SEQUENCE {
protocolIEs ProtocolIE-Container { {LocationReportingControlIEs} },
...
}
LocationReportingControlIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-LocationReportingRequestType CRITICALITY ignore TYPE LocationReportingRequestType PRESENCE mandatory },
...
}
-- **************************************************************
--
-- LOCATION REPORTING FAILURE INDICATION
--
-- **************************************************************
LocationReportingFailureIndication ::= SEQUENCE {
protocolIEs ProtocolIE-Container { {LocationReportingFailureIndicationIEs} },
...
}
LocationReportingFailureIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-Cause CRITICALITY ignore TYPE Cause PRESENCE mandatory },
...
}
-- **************************************************************
--
-- LOCATION REPORT
--
-- **************************************************************
LocationReport ::= SEQUENCE {
protocolIEs ProtocolIE-Container { {LocationReportIEs} },
...
}
LocationReportIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UserLocationInformation CRITICALITY ignore TYPE UserLocationInformation PRESENCE mandatory }|
{ ID id-UEPresenceInAreaOfInterestList CRITICALITY ignore TYPE UEPresenceInAreaOfInterestList PRESENCE optional }|
{ ID id-LocationReportingRequestType CRITICALITY ignore TYPE LocationReportingRequestType PRESENCE mandatory },
...
}
-- **************************************************************
--
-- UE TNLA BINDING ELEMENTARY PROCEDURES
--
-- **************************************************************
-- **************************************************************
--
-- UE TNLA BINDING RELEASE REQUEST
--
-- **************************************************************
UETNLABindingReleaseRequest ::= SEQUENCE {
protocolIEs ProtocolIE-Container { {UETNLABindingReleaseRequestIEs} },
...
}
UETNLABindingReleaseRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory },
...
}
-- **************************************************************
--
-- UE RADIO CAPABILITY MANAGEMENT ELEMENTARY PROCEDURES
--
-- **************************************************************
-- **************************************************************
--
-- UE RADIO CAPABILITY INFO INDICATION
--
-- **************************************************************
UERadioCapabilityInfoIndication ::= SEQUENCE {
protocolIEs ProtocolIE-Container { {UERadioCapabilityInfoIndicationIEs} },
...
}
UERadioCapabilityInfoIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UERadioCapability CRITICALITY ignore TYPE UERadioCapability PRESENCE mandatory }|
{ ID id-UERadioCapabilityForPaging CRITICALITY ignore TYPE UERadioCapabilityForPaging PRESENCE optional }|
{ ID id-UERadioCapability-EUTRA-Format CRITICALITY ignore TYPE UERadioCapability PRESENCE optional }|
{ ID id-XrDeviceWith2Rx CRITICALITY ignore TYPE XrDeviceWith2Rx PRESENCE optional },
...
}
-- **************************************************************
--
-- UE Radio Capability Check Elementary Procedure
--
-- **************************************************************
-- **************************************************************
--
-- UE RADIO CAPABILITY CHECK REQUEST
--
-- **************************************************************
UERadioCapabilityCheckRequest ::= SEQUENCE {
protocolIEs ProtocolIE-Container { {UERadioCapabilityCheckRequestIEs} },
...
}
UERadioCapabilityCheckRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UERadioCapability CRITICALITY ignore TYPE UERadioCapability PRESENCE optional }|
{ ID id-UERadioCapabilityID CRITICALITY reject TYPE UERadioCapabilityID PRESENCE optional },
...
}
-- **************************************************************
--
-- UE RADIO CAPABILITY CHECK RESPONSE
--
-- **************************************************************
UERadioCapabilityCheckResponse ::= SEQUENCE {
protocolIEs ProtocolIE-Container { {UERadioCapabilityCheckResponseIEs} },
...
}
UERadioCapabilityCheckResponseIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-IMSVoiceSupportIndicator CRITICALITY reject TYPE IMSVoiceSupportIndicator PRESENCE mandatory }|
{ ID id-CriticalityDiagnostics CRITICALITY ignore TYPE CriticalityDiagnostics PRESENCE optional },
...
}
-- **************************************************************
--
-- PRIVATE MESSAGE ELEMENTARY PROCEDURE
--
-- **************************************************************
-- **************************************************************
--
-- PRIVATE MESSAGE
--
-- **************************************************************
PrivateMessage ::= SEQUENCE {
privateIEs PrivateIE-Container { { PrivateMessageIEs } },
...
}
PrivateMessageIEs NGAP-PRIVATE-IES ::= {
...
}
-- **************************************************************
--
-- DATA USAGE REPORTING ELEMENTARY PROCEDURES
--
-- **************************************************************
-- **************************************************************
--
-- SECONDARY RAT DATA USAGE REPORT
--
-- **************************************************************
SecondaryRATDataUsageReport ::= SEQUENCE {
protocolIEs ProtocolIE-Container { {SecondaryRATDataUsageReportIEs} },
...
}
SecondaryRATDataUsageReportIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PDUSessionResourceSecondaryRATUsageList CRITICALITY ignore TYPE PDUSessionResourceSecondaryRATUsageList PRESENCE mandatory }|
{ ID id-HandoverFlag CRITICALITY ignore TYPE HandoverFlag PRESENCE optional }|
{ ID id-UserLocationInformation CRITICALITY ignore TYPE UserLocationInformation PRESENCE optional },
...
}
-- **************************************************************
--
-- RIM INFORMATION TRANSFER ELEMENTARY PROCEDURES
--
-- **************************************************************
-- **************************************************************
--
-- UPLINK RIM INFORMATION TRANSFER
--
-- **************************************************************
UplinkRIMInformationTransfer ::= SEQUENCE {
protocolIEs ProtocolIE-Container { {UplinkRIMInformationTransferIEs} },
...
}
UplinkRIMInformationTransferIEs NGAP-PROTOCOL-IES ::= {
{ ID id-RIMInformationTransfer CRITICALITY ignore TYPE RIMInformationTransfer PRESENCE optional },
...
}
-- **************************************************************
--
-- DOWNLINK RIM INFORMATION TRANSFER
--
-- **************************************************************
DownlinkRIMInformationTransfer ::= SEQUENCE {
protocolIEs ProtocolIE-Container { {DownlinkRIMInformationTransferIEs} },
...
}
DownlinkRIMInformationTransferIEs NGAP-PROTOCOL-IES ::= {
{ ID id-RIMInformationTransfer CRITICALITY ignore TYPE RIMInformationTransfer PRESENCE optional },
...
}
-- **************************************************************
--
-- Connection Establishment Indication
--
-- **************************************************************
ConnectionEstablishmentIndication::= SEQUENCE {
protocolIEs ProtocolIE-Container { {ConnectionEstablishmentIndicationIEs} },
...
}
ConnectionEstablishmentIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-UERadioCapability CRITICALITY ignore TYPE UERadioCapability PRESENCE optional }|
{ ID id-EndIndication CRITICALITY ignore TYPE EndIndication PRESENCE optional }|
{ ID id-S-NSSAI CRITICALITY ignore TYPE S-NSSAI PRESENCE optional }|
{ ID id-AllowedNSSAI CRITICALITY ignore TYPE AllowedNSSAI PRESENCE optional }|
{ ID id-UE-DifferentiationInfo CRITICALITY ignore TYPE UE-DifferentiationInfo PRESENCE optional }|
{ ID id-DL-CP-SecurityInformation CRITICALITY ignore TYPE DL-CP-SecurityInformation PRESENCE optional }|
{ ID id-NB-IoT-UEPriority CRITICALITY ignore TYPE NB-IoT-UEPriority PRESENCE optional }|
{ ID id-Enhanced-CoverageRestriction CRITICALITY ignore TYPE Enhanced-CoverageRestriction PRESENCE optional }|
{ ID id-CEmodeBrestricted CRITICALITY ignore TYPE CEmodeBrestricted PRESENCE optional }|
{ ID id-UERadioCapabilityID CRITICALITY reject TYPE UERadioCapabilityID PRESENCE optional }|
{ ID id-MaskedIMEISV CRITICALITY ignore TYPE MaskedIMEISV PRESENCE optional }|
{ ID id-OldAMF CRITICALITY reject TYPE AMFName PRESENCE optional }|
{ ID id-Partially-Allowed-NSSAI CRITICALITY ignore TYPE Partially-Allowed-NSSAI PRESENCE optional }|
{ ID id-ExtendedOldAMF CRITICALITY ignore TYPE Extended-AMFName PRESENCE optional },
...
}
-- **************************************************************
--
-- UE RADIO CAPABILITY ID MAPPING ELEMENTARY PROCEDURES
--
-- **************************************************************
-- **************************************************************
--
-- UE RADIO CAPABILITY ID MAPPING REQUEST
--
-- **************************************************************
UERadioCapabilityIDMappingRequest ::= SEQUENCE {
protocolIEs ProtocolIE-Container { {UERadioCapabilityIDMappingRequestIEs} },
...
}
UERadioCapabilityIDMappingRequestIEs NGAP-PROTOCOL-IES ::= {
{ ID id-UERadioCapabilityID CRITICALITY reject TYPE UERadioCapabilityID PRESENCE mandatory },
...
}
-- **************************************************************
--
-- UE RADIO CAPABILITY ID MAPPING RESPONSE
--
-- **************************************************************
UERadioCapabilityIDMappingResponse ::= SEQUENCE {
protocolIEs ProtocolIE-Container { {UERadioCapabilityIDMappingResponseIEs} },
...
}
UERadioCapabilityIDMappingResponseIEs NGAP-PROTOCOL-IES ::= {
{ ID id-UERadioCapabilityID CRITICALITY reject TYPE UERadioCapabilityID PRESENCE mandatory }|
{ ID id-UERadioCapability CRITICALITY ignore TYPE UERadioCapability PRESENCE mandatory }|
{ ID id-CriticalityDiagnostics CRITICALITY ignore TYPE CriticalityDiagnostics PRESENCE optional },
...
}
-- **************************************************************
--
-- AMF CP Relocation Indication
--
-- **************************************************************
AMFCPRelocationIndication ::= SEQUENCE {
protocolIEs ProtocolIE-Container { { AMFCPRelocationIndicationIEs} },
...
}
AMFCPRelocationIndicationIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-S-NSSAI CRITICALITY ignore TYPE S-NSSAI PRESENCE optional }| --this IE is not used and ignored
{ ID id-AllowedNSSAI CRITICALITY ignore TYPE AllowedNSSAI PRESENCE optional }| --this IE is not used and ignored
{ ID id-Partially-Allowed-NSSAI CRITICALITY ignore TYPE Partially-Allowed-NSSAI PRESENCE optional }, --this IE is not used and ignored
...
}
-- **************************************************************
--
-- MBS SESSION MANAGEMENT ELEMENTARY PROCEDURES
--
-- **************************************************************
-- **************************************************************
--
-- Broadcast Session Setup Elementary Procedure
--
-- **************************************************************
-- **************************************************************
--
-- BROADCAST SESSION SETUP REQUEST
--
-- **************************************************************
BroadcastSessionSetupRequest ::= SEQUENCE {
protocolIEs ProtocolIE-Container { {BroadcastSessionSetupRequestIEs} },
...
}
BroadcastSessionSetupRequestIEs NGAP-PROTOCOL-IES ::= {
{ ID id-MBS-SessionID CRITICALITY reject TYPE MBS-SessionID PRESENCE mandatory }|
{ ID id-S-NSSAI CRITICALITY reject TYPE S-NSSAI PRESENCE mandatory }|
{ ID id-MBS-ServiceArea CRITICALITY reject TYPE MBS-ServiceArea PRESENCE mandatory }|
{ ID id-MBSSessionSetupRequestTransfer CRITICALITY reject TYPE OCTET STRING (CONTAINING MBSSessionSetupOrModRequestTransfer) PRESENCE mandatory }|
{ ID id-AssociatedSessionID CRITICALITY ignore TYPE AssociatedSessionID PRESENCE optional },
...
}
-- **************************************************************
--
-- BROADCAST SESSION SETUP RESPONSE
--
-- **************************************************************
BroadcastSessionSetupResponse ::= SEQUENCE {
protocolIEs ProtocolIE-Container { {BroadcastSessionSetupResponseIEs} },
...
}
BroadcastSessionSetupResponseIEs NGAP-PROTOCOL-IES ::= {
{ ID id-MBS-SessionID CRITICALITY reject TYPE MBS-SessionID PRESENCE mandatory }|
{ ID id-MBSSessionSetupResponseTransfer CRITICALITY reject TYPE OCTET STRING (CONTAINING MBSSessionSetupOrModResponseTransfer) PRESENCE optional }|
{ ID id-CriticalityDiagnostics CRITICALITY ignore TYPE CriticalityDiagnostics PRESENCE optional },
...
}
-- **************************************************************
--
-- BROADCAST SESSION SETUP FAILURE
--
-- **************************************************************
BroadcastSessionSetupFailure ::= SEQUENCE {
protocolIEs ProtocolIE-Container { {BroadcastSessionSetupFailureIEs} },
...
}
BroadcastSessionSetupFailureIEs NGAP-PROTOCOL-IES ::= {
{ ID id-MBS-SessionID CRITICALITY reject TYPE MBS-SessionID PRESENCE mandatory }|
{ ID id-MBSSessionSetupFailureTransfer CRITICALITY ignore TYPE OCTET STRING (CONTAINING MBSSessionSetupOrModFailureTransfer ) PRESENCE optional }|
{ ID id-Cause CRITICALITY ignore TYPE Cause PRESENCE mandatory }|
{ ID id-CriticalityDiagnostics CRITICALITY ignore TYPE CriticalityDiagnostics PRESENCE optional },
...
}
-- **************************************************************
--
-- Broadcast Session Modification Elementary Procedure
--
-- **************************************************************
-- **************************************************************
--
-- BROADCAST SESSION MODIFICATION REQUEST
--
-- **************************************************************
BroadcastSessionModificationRequest ::= SEQUENCE {
protocolIEs ProtocolIE-Container { {BroadcastSessionModificationRequestIEs} },
...
}
BroadcastSessionModificationRequestIEs NGAP-PROTOCOL-IES ::= {
{ ID id-MBS-SessionID CRITICALITY reject TYPE MBS-SessionID PRESENCE mandatory }|
{ ID id-MBS-ServiceArea CRITICALITY reject TYPE MBS-ServiceArea PRESENCE optional }|
{ ID id-MBSSessionModificationRequestTransfer CRITICALITY reject TYPE OCTET STRING (CONTAINING MBSSessionSetupOrModRequestTransfer) PRESENCE optional },
...
}
-- **************************************************************
--
-- BROADCAST SESSION MODIFICATION RESPONSE
--
-- **************************************************************
BroadcastSessionModificationResponse ::= SEQUENCE {
protocolIEs ProtocolIE-Container { {BroadcastSessionModificationResponseIEs} },
...
}
BroadcastSessionModificationResponseIEs NGAP-PROTOCOL-IES ::= {
{ ID id-MBS-SessionID CRITICALITY reject TYPE MBS-SessionID PRESENCE mandatory }|
{ ID id-MBSSessionModificationResponseTransfer CRITICALITY reject TYPE OCTET STRING (CONTAINING MBSSessionSetupOrModResponseTransfer) PRESENCE optional }|
{ ID id-CriticalityDiagnostics CRITICALITY ignore TYPE CriticalityDiagnostics PRESENCE optional },
...
}
-- **************************************************************
--
-- BROADCAST SESSION MODIFICATION FAILURE
--
-- **************************************************************
BroadcastSessionModificationFailure ::= SEQUENCE {
protocolIEs ProtocolIE-Container { {BroadcastSessionModificationFailureIEs} },
...
}
BroadcastSessionModificationFailureIEs NGAP-PROTOCOL-IES ::= {
{ ID id-MBS-SessionID CRITICALITY reject TYPE MBS-SessionID PRESENCE mandatory }|
{ ID id-MBSSessionModificationFailureTransfer CRITICALITY ignore TYPE OCTET STRING (CONTAINING MBSSessionSetupOrModFailureTransfer) PRESENCE optional }|
{ ID id-Cause CRITICALITY ignore TYPE Cause PRESENCE mandatory }|
{ ID id-CriticalityDiagnostics CRITICALITY ignore TYPE CriticalityDiagnostics PRESENCE optional },
...
}
-- **************************************************************
--
-- Broadcast Session Release Elementary Procedure
--
-- **************************************************************
-- **************************************************************
--
-- BROADCAST SESSION RELEASE REQUEST
--
-- **************************************************************
BroadcastSessionReleaseRequest ::= SEQUENCE {
protocolIEs ProtocolIE-Container { {BroadcastSessionReleaseRequestIEs} },
...
}
BroadcastSessionReleaseRequestIEs NGAP-PROTOCOL-IES ::= {
{ ID id-MBS-SessionID CRITICALITY reject TYPE MBS-SessionID PRESENCE mandatory }|
{ ID id-Cause CRITICALITY ignore TYPE Cause PRESENCE mandatory },
...
}
-- **************************************************************
--
-- Broadcast Session Release Required Elementary Procedure
--
-- **************************************************************
-- **************************************************************
--
-- BROADCAST SESSION RELEASE REQUIRED
--
-- **************************************************************
BroadcastSessionReleaseRequired ::= SEQUENCE {
protocolIEs ProtocolIE-Container { {BroadcastSessionReleaseRequiredIEs} },
...
}
BroadcastSessionReleaseRequiredIEs NGAP-PROTOCOL-IES ::= {
{ ID id-MBS-SessionID CRITICALITY reject TYPE MBS-SessionID PRESENCE mandatory }|
{ ID id-Cause CRITICALITY ignore TYPE Cause PRESENCE mandatory },
...
}
-- **************************************************************
--
-- BROADCAST SESSION RELEASE RESPONSE
--
-- **************************************************************
BroadcastSessionReleaseResponse ::= SEQUENCE {
protocolIEs ProtocolIE-Container { {BroadcastSessionReleaseResponseIEs} },
...
}
BroadcastSessionReleaseResponseIEs NGAP-PROTOCOL-IES ::= {
{ ID id-MBS-SessionID CRITICALITY reject TYPE MBS-SessionID PRESENCE mandatory }|
{ ID id-MBSSessionReleaseResponseTransfer CRITICALITY ignore TYPE OCTET STRING (CONTAINING MBSSessionReleaseResponseTransfer) PRESENCE optional }|
{ ID id-CriticalityDiagnostics CRITICALITY ignore TYPE CriticalityDiagnostics PRESENCE optional },
...
}
-- **************************************************************
--
-- Broadcast Session Transport Elementary Procedure
--
-- **************************************************************
-- **************************************************************
--
-- BROADCAST SESSION TRANSPORT REQUEST
--
-- **************************************************************
BroadcastSessionTransportRequest ::= SEQUENCE {
protocolIEs ProtocolIE-Container { {BroadcastSessionTransportRequestIEs} },
...
}
BroadcastSessionTransportRequestIEs NGAP-PROTOCOL-IES ::= {
{ ID id-MBS-SessionID CRITICALITY reject TYPE MBS-SessionID PRESENCE mandatory }|
{ ID id-BroadcastTransportRequestTransfer CRITICALITY reject TYPE OCTET STRING (CONTAINING BroadcastTransportRequestTransfer) PRESENCE mandatory },
...
}
-- **************************************************************
--
-- BROADCAST SESSION TRANSPORT RESPONSE
--
-- **************************************************************
BroadcastSessionTransportResponse ::= SEQUENCE {
protocolIEs ProtocolIE-Container { {BroadcastSessionTransportResponseIEs} },
...
}
BroadcastSessionTransportResponseIEs NGAP-PROTOCOL-IES ::= {
{ ID id-MBS-SessionID CRITICALITY reject TYPE MBS-SessionID PRESENCE mandatory }|
{ ID id-BroadcastTransportResponseTransfer CRITICALITY reject TYPE OCTET STRING (CONTAINING BroadcastTransportResponseTransfer) PRESENCE mandatory }|
{ ID id-CriticalityDiagnostics CRITICALITY ignore TYPE CriticalityDiagnostics PRESENCE optional },
...
}
-- **************************************************************
--
-- BROADCAST SESSION TRANSPORT FAILURE
--
-- **************************************************************
BroadcastSessionTransportFailure ::= SEQUENCE {
protocolIEs ProtocolIE-Container { {BroadcastSessionTransportFailureIEs} },
...
}
BroadcastSessionTransportFailureIEs NGAP-PROTOCOL-IES ::= {
{ ID id-MBS-SessionID CRITICALITY reject TYPE MBS-SessionID PRESENCE mandatory }|
{ ID id-BroadcastTransportFailureTransfer CRITICALITY ignore TYPE OCTET STRING (CONTAINING BroadcastTransportFailureTransfer) PRESENCE mandatory }|
{ ID id-Cause CRITICALITY ignore TYPE Cause PRESENCE mandatory }|
{ ID id-CriticalityDiagnostics CRITICALITY ignore TYPE CriticalityDiagnostics PRESENCE optional },
...
}
-- **************************************************************
--
-- Distribution Setup Elementary Procedure
--
-- **************************************************************
-- **************************************************************
--
-- DISTRIBUTION SETUP REQUEST
--
-- **************************************************************
DistributionSetupRequest ::= SEQUENCE {
protocolIEs ProtocolIE-Container { {DistributionSetupRequestIEs} },
...
}
DistributionSetupRequestIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-MBS-DistributionSetupRequestTransfer CRITICALITY reject TYPE OCTET STRING (CONTAINING MBS-DistributionSetupRequestTransfer) PRESENCE mandatory },
...
}
-- **************************************************************
--
-- DISTRIBUTION SETUP RESPONSE
--
-- **************************************************************
DistributionSetupResponse ::= SEQUENCE {
protocolIEs ProtocolIE-Container { {DistributionSetupResponseIEs} },
...
}
DistributionSetupResponseIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-MBS-DistributionSetupResponseTransfer CRITICALITY reject TYPE OCTET STRING (CONTAINING MBS-DistributionSetupResponseTransfer) PRESENCE mandatory }|
{ ID id-CriticalityDiagnostics CRITICALITY ignore TYPE CriticalityDiagnostics PRESENCE optional },
...
}
-- **************************************************************
--
-- DISTRIBUTION SETUP FAILURE
--
-- **************************************************************
DistributionSetupFailure ::= SEQUENCE {
protocolIEs ProtocolIE-Container { {DistributionSetupFailureIEs} },
...
}
DistributionSetupFailureIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-MBS-DistributionSetupUnsuccessfulTransfer CRITICALITY ignore TYPE OCTET STRING (CONTAINING MBS-DistributionSetupUnsuccessfulTransfer) PRESENCE mandatory }|
{ ID id-Cause CRITICALITY ignore TYPE Cause PRESENCE mandatory }|
{ ID id-CriticalityDiagnostics CRITICALITY ignore TYPE CriticalityDiagnostics PRESENCE optional },
...
}
-- **************************************************************
--
-- Distribution Release Elementary Procedure
--
-- **************************************************************
-- **************************************************************
--
-- DISTRIBUTION RELEASE REQUEST
--
-- **************************************************************
DistributionReleaseRequest ::= SEQUENCE {
protocolIEs ProtocolIE-Container { {DistributionReleaseRequestIEs} },
...
}
DistributionReleaseRequestIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-MBS-DistributionReleaseRequestTransfer CRITICALITY reject TYPE OCTET STRING (CONTAINING MBS-DistributionReleaseRequestTransfer) PRESENCE mandatory }|
{ ID id-Cause CRITICALITY ignore TYPE Cause PRESENCE mandatory },
...
}
-- **************************************************************
--
-- DISTRIBUTION RELEASE RESPONSE
--
-- **************************************************************
DistributionReleaseResponse ::= SEQUENCE {
protocolIEs ProtocolIE-Container { {DistributionReleaseResponseIEs} },
...
}
DistributionReleaseResponseIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-CriticalityDiagnostics CRITICALITY ignore TYPE CriticalityDiagnostics PRESENCE optional },
...
}
-- **************************************************************
--
-- Multicast Session Activation Elementary Procedure
--
-- **************************************************************
-- **************************************************************
--
-- MULTICAST SESSION ACTIVATION REQUEST
--
-- **************************************************************
MulticastSessionActivationRequest ::= SEQUENCE {
protocolIEs ProtocolIE-Container { {MulticastSessionActivationRequestIEs} },
...
}
MulticastSessionActivationRequestIEs NGAP-PROTOCOL-IES ::= {
{ ID id-MBS-SessionID CRITICALITY reject TYPE MBS-SessionID PRESENCE mandatory }|
{ ID id-MulticastSessionActivationRequestTransfer CRITICALITY reject TYPE OCTET STRING (CONTAINING MulticastSessionActivationRequestTransfer) PRESENCE mandatory },
...
}
-- **************************************************************
--
-- MULTICAST SESSION ACTIVATION RESPONSE
--
-- **************************************************************
MulticastSessionActivationResponse ::= SEQUENCE {
protocolIEs ProtocolIE-Container { {MulticastSessionActivationResponseIEs} },
...
}
MulticastSessionActivationResponseIEs NGAP-PROTOCOL-IES ::= {
{ ID id-MBS-SessionID CRITICALITY reject TYPE MBS-SessionID PRESENCE mandatory }|
{ ID id-CriticalityDiagnostics CRITICALITY ignore TYPE CriticalityDiagnostics PRESENCE optional },
...
}
-- **************************************************************
--
-- MULTICAST SESSION ACTIVATION FAILURE
--
-- **************************************************************
MulticastSessionActivationFailure ::= SEQUENCE {
protocolIEs ProtocolIE-Container { {MulticastSessionActivationFailureIEs} },
...
}
MulticastSessionActivationFailureIEs NGAP-PROTOCOL-IES ::= {
{ ID id-MBS-SessionID CRITICALITY reject TYPE MBS-SessionID PRESENCE mandatory }|
{ ID id-Cause CRITICALITY ignore TYPE Cause PRESENCE mandatory }|
{ ID id-CriticalityDiagnostics CRITICALITY ignore TYPE CriticalityDiagnostics PRESENCE optional },
...
}
-- **************************************************************
--
-- Multicast Session Deactivation Elementary Procedure
--
-- **************************************************************
-- **************************************************************
--
-- MULTICAST SESSION DEACTIVATION REQUEST
--
-- **************************************************************
MulticastSessionDeactivationRequest ::= SEQUENCE {
protocolIEs ProtocolIE-Container { {MulticastSessionDeactivationRequestIEs} },
...
}
MulticastSessionDeactivationRequestIEs NGAP-PROTOCOL-IES ::= {
{ ID id-MBS-SessionID CRITICALITY reject TYPE MBS-SessionID PRESENCE mandatory }|
{ ID id-MulticastSessionDeactivationRequestTransfer CRITICALITY reject TYPE OCTET STRING (CONTAINING MulticastSessionDeactivationRequestTransfer) PRESENCE mandatory },
...
}
-- **************************************************************
--
-- MULTICAST SESSION DEACTIVATION RESPONSE
--
-- **************************************************************
MulticastSessionDeactivationResponse ::= SEQUENCE {
protocolIEs ProtocolIE-Container { {MulticastSessionDeactivationResponseIEs} },
...
}
MulticastSessionDeactivationResponseIEs NGAP-PROTOCOL-IES ::= {
{ ID id-MBS-SessionID CRITICALITY reject TYPE MBS-SessionID PRESENCE mandatory }|
{ ID id-CriticalityDiagnostics CRITICALITY ignore TYPE CriticalityDiagnostics PRESENCE optional },
...
}
-- **************************************************************
--
-- Multicast Session Update Elementary Procedure
--
-- **************************************************************
-- **************************************************************
--
-- MULTICAST SESSION UPDATE REQUEST
--
-- **************************************************************
MulticastSessionUpdateRequest ::= SEQUENCE {
protocolIEs ProtocolIE-Container { {MulticastSessionUpdateRequestIEs} },
...
}
MulticastSessionUpdateRequestIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-MulticastSessionUpdateRequestTransfer CRITICALITY reject TYPE OCTET STRING (CONTAINING MulticastSessionUpdateRequestTransfer) PRESENCE mandatory },
...
}
-- **************************************************************
--
-- MULTICAST SESSION UPDATE RESPONSE
--
-- **************************************************************
MulticastSessionUpdateResponse ::= SEQUENCE {
protocolIEs ProtocolIE-Container { {MulticastSessionUpdateResponseIEs} },
...
}
MulticastSessionUpdateResponseIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-CriticalityDiagnostics CRITICALITY ignore TYPE CriticalityDiagnostics PRESENCE optional },
...
}
-- **************************************************************
--
-- MULTICAST SESSION UPDATE FAILURE
--
-- **************************************************************
MulticastSessionUpdateFailure ::= SEQUENCE {
protocolIEs ProtocolIE-Container { {MulticastSessionUpdateFailureIEs} },
...
}
MulticastSessionUpdateFailureIEs NGAP-PROTOCOL-IES ::= {
{ ID id-MBS-SessionID CRITICALITY reject TYPE MBS-SessionID PRESENCE mandatory }|
{ ID id-MBS-AreaSessionID CRITICALITY reject TYPE MBS-AreaSessionID PRESENCE optional }|
{ ID id-Cause CRITICALITY ignore TYPE Cause PRESENCE mandatory }|
{ ID id-CriticalityDiagnostics CRITICALITY ignore TYPE CriticalityDiagnostics PRESENCE optional },
...
}
-- **************************************************************
--
-- MULTICAST GROUP PAGING ELEMENTARY PROCEDURE
--
-- **************************************************************
-- **************************************************************
--
-- MULTICAST GROUP PAGING
--
-- **************************************************************
MulticastGroupPaging ::= SEQUENCE {
protocolIEs ProtocolIE-Container { {MulticastGroupPagingIEs} },
...
}
MulticastGroupPagingIEs NGAP-PROTOCOL-IES ::= {
{ ID id-MBS-SessionID CRITICALITY ignore TYPE MBS-SessionID PRESENCE mandatory }|
{ ID id-MBS-ServiceArea CRITICALITY ignore TYPE MBS-ServiceArea PRESENCE optional }|
{ ID id-MulticastGroupPagingAreaList CRITICALITY ignore TYPE MulticastGroupPagingAreaList PRESENCE mandatory },
...
}
-- **************************************************************
--
-- TIMING SYNCHRONISATION STATUS REPORTING ELEMENTARY PROCEDURES
--
-- **************************************************************
-- **************************************************************
--
-- Timing Synchronisation Status Elementary Procedure
--
-- **************************************************************
-- **************************************************************
--
-- TIMING SYNCHRONISATION STATUS REQUEST
--
-- **************************************************************
TimingSynchronisationStatusRequest ::= SEQUENCE {
protocolIEs ProtocolIE-Container { {TimingSynchronisationStatusRequestIEs} },
...
}
TimingSynchronisationStatusRequestIEs NGAP-PROTOCOL-IES ::= {
{ ID id-RoutingID CRITICALITY reject TYPE RoutingID PRESENCE mandatory }|
{ ID id-RAN-TSSRequestType CRITICALITY reject TYPE RAN-TSSRequestType PRESENCE mandatory },
...
}
-- **************************************************************
--
-- TIMING SYNCHRONISATION STATUS RESPONSE
--
-- **************************************************************
TimingSynchronisationStatusResponse ::= SEQUENCE {
protocolIEs ProtocolIE-Container { {TimingSynchronisationStatusResponseIEs} },
...
}
TimingSynchronisationStatusResponseIEs NGAP-PROTOCOL-IES ::= {
{ ID id-RoutingID CRITICALITY ignore TYPE RoutingID PRESENCE mandatory }|
{ ID id-CriticalityDiagnostics CRITICALITY ignore TYPE CriticalityDiagnostics PRESENCE optional },
...
}
-- **************************************************************
--
-- TIMING SYNCHRONISATION STATUS FAILURE
--
-- **************************************************************
TimingSynchronisationStatusFailure ::= SEQUENCE {
protocolIEs ProtocolIE-Container { { TimingSynchronisationStatusFailureIEs} },
...
}
TimingSynchronisationStatusFailureIEs NGAP-PROTOCOL-IES ::= {
{ ID id-RoutingID CRITICALITY ignore TYPE RoutingID PRESENCE mandatory }|
{ ID id-Cause CRITICALITY ignore TYPE Cause PRESENCE mandatory }|
{ ID id-CriticalityDiagnostics CRITICALITY ignore TYPE CriticalityDiagnostics PRESENCE optional },
...
}
-- **************************************************************
--
-- Timing Synchronisation Status Reporting Elementary Procedure
--
-- **************************************************************
-- **************************************************************
--
-- TIMING SYNCHRONISATION STATUS REPORT
--
-- **************************************************************
TimingSynchronisationStatusReport ::= SEQUENCE {
protocolIEs ProtocolIE-Container { {TimingSynchronisationStatusReportIEs} },
...
}
TimingSynchronisationStatusReportIEs NGAP-PROTOCOL-IES ::= {
{ ID id-RoutingID CRITICALITY ignore TYPE RoutingID PRESENCE mandatory }|
{ ID id-RANTimingSynchronisationStatusInfo CRITICALITY ignore TYPE RANTimingSynchronisationStatusInfo PRESENCE mandatory }|
{ ID id-RAN-TSSScope CRITICALITY ignore TYPE RAN-TSSScope PRESENCE mandatory },
...
}
-- **************************************************************
--
-- MT Communication Handling Elementary Procedure
--
-- **************************************************************
-- **************************************************************
--
-- MT COMMUNICATION HANDLING REQUEST
--
-- **************************************************************
MTCommunicationHandlingRequest ::= SEQUENCE {
protocolIEs ProtocolIE-Container { { MTCommunicationHandlingRequestIEs} },
...
}
MTCommunicationHandlingRequestIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-FiveGCAction CRITICALITY reject TYPE FiveGCAction PRESENCE mandatory }|
{ ID id-PDUSessionListMTCommHReq CRITICALITY reject TYPE PDUSessionListMTCommHReq PRESENCE mandatory },
...
}
-- **************************************************************
--
-- MT COMMUNICATION HANDLING RESPONSE
--
-- **************************************************************
MTCommunicationHandlingResponse ::= SEQUENCE {
protocolIEs ProtocolIE-Container { {MTCommunicationHandlingResponseIEs} },
...
}
MTCommunicationHandlingResponseIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-CriticalityDiagnostics CRITICALITY ignore TYPE CriticalityDiagnostics PRESENCE optional },
...
}
-- **************************************************************
--
-- MT COMMUNICATION HANDLING FAILURE
--
-- **************************************************************
MTCommunicationHandlingFailure ::= SEQUENCE {
protocolIEs ProtocolIE-Container { { MTCommunicationHandlingFailureIEs} },
...
}
MTCommunicationHandlingFailureIEs NGAP-PROTOCOL-IES ::= {
{ ID id-AMF-UE-NGAP-ID CRITICALITY reject TYPE AMF-UE-NGAP-ID PRESENCE mandatory }|
{ ID id-RAN-UE-NGAP-ID CRITICALITY reject TYPE RAN-UE-NGAP-ID PRESENCE mandatory }|
{ ID id-Cause CRITICALITY ignore TYPE Cause PRESENCE mandatory }|
{ ID id-CriticalityDiagnostics CRITICALITY ignore TYPE CriticalityDiagnostics PRESENCE optional },
...
}
-- **************************************************************
-- RAN Paging Request procedure
--
-- **************************************************************
-- **************************************************************
--
-- RAN PAGING REQUEST
--
-- **************************************************************
RANPagingRequest ::= SEQUENCE {
protocolIEs ProtocolIE-Container { { RANPagingRequestIEs} },
...
}
RANPagingRequestIEs NGAP-PROTOCOL-IES ::= {
{ ID id-AMF-UE-NGAP-ID CRITICALITY ignore TYPE AMF-UE-NGAP-ID PRESENCE mandatory }|
{ ID id-RAN-UE-NGAP-ID CRITICALITY ignore TYPE RAN-UE-NGAP-ID PRESENCE mandatory }|
{ ID id-PagingPolicyDifferentiation CRITICALITY ignore TYPE PagingPolicyDifferentiation PRESENCE optional }|
{ ID id-DL-Signalling CRITICALITY ignore TYPE DL-Signalling PRESENCE optional },
...
}
END

-- **************************************************************
--
-- Information Element Definitions
--
-- **************************************************************
NGAP-IEs {
itu-t (0) identified-organization (4) etsi (0) mobileDomain (0)
ngran-Access (22) modules (3) ngap (1) version1 (1) ngap-IEs (2) }
DEFINITIONS AUTOMATIC TAGS ::=
BEGIN
IMPORTS
id-AdditionalDLForwardingUPTNLInformation,
id-AdditionalULForwardingUPTNLInformation,
id-AdditionalDLQosFlowPerTNLInformation,
id-AdditionalDLUPTNLInformationForHOList,
id-AdditionalNGU-UP-TNLInformation,
id-AdditionalRedundantDL-NGU-UP-TNLInformation,
id-AdditionalRedundantDLQosFlowPerTNLInformation,
id-AdditionalRedundantNGU-UP-TNLInformation,
id-AdditionalRedundantUL-NGU-UP-TNLInformation,
id-AdditionalUL-NGU-UP-TNLInformation,
id-AlternativeQoSParaSetList,
id-AssistanceInformationQoE-Meas,
id-AdditionalCancelledlocationReportingReferenceIDList,
id-BurstArrivalTimeDownlink,
id-Cause,
id-CNPacketDelayBudgetDL,
id-CNPacketDelayBudgetUL,
id-CNTypeRestrictionsForEquivalent,
id-CNTypeRestrictionsForServing,
id-CommonNetworkInstance,
id-ConfiguredTACIndication,
id-CN-MT-CommunicationHandling,
id-CurrentQoSParaSetIndex,
id-DAPSRequestInfo,
id-DAPSResponseInfoList,
id-DataForwardingNotPossible,
id-DataForwardingResponseERABList,
id-DirectForwardingPathAvailability,
id-DL-NGU-UP-TNLInformation,
id-DownlinkTLContainer,
id-EndpointIPAddressAndPort,
id-EnergySavingIndication,
id-ExtendedMobilityInformation,
id-ExtendedPacketDelayBudget,
id-ExtendedRATRestrictionInformation,
id-ExtendedReportIntervalMDT,
id-ExtendedSliceSupportList,
id-ExtendedTAISliceSupportList,
id-ExtendedUEIdentityIndexValue,
id-EUTRA-PagingeDRXInformation,
id-EquivalentSNPNsList,
id-GlobalCable-ID,
id-GlobalRANNodeID,
id-GlobalTNGF-ID,
id-GlobalTWIF-ID,
id-GlobalW-AGF-ID,
id-GUAMIType,
id-HashedUEIdentityIndexValue,
id-IncludeBeamMeasurementsIndication,
id-IntersystemSONInformationRequest,
id-IntersystemSONInformationReply,
id-IntersystemResourceStatusUpdate,
id-IntersystemMobilityFailureforVoiceFallback,
id-LastEUTRAN-PLMNIdentity,
id-LastVisitedPSCellList,
id-LocationReportingAdditionalInfo,
id-M4ReportAmount,
id-M5ReportAmount,
id-M6ReportAmount,
id-ExcessPacketDelayThresholdConfiguration,
id-M7ReportAmount,
id-MaximumIntegrityProtectedDataRate-DL,
id-MBS-AreaSessionID,
id-MBS-QoSFlowsToBeSetupList,
id-MBS-QoSFlowsToBeSetupModList,
id-MBS-QoSFlowToReleaseList,
id-MBS-ServiceArea,
id-MBS-SessionFSAIDList,
id-MBS-SessionID,
id-MBS-ActiveSessionInformation-SourcetoTargetList,
id-MBS-ActiveSessionInformation-TargettoSourceList,
id-MBS-AssistanceInformation,
id-MBS-SessionTNLInfo5GC,
id-MBS-SupportIndicator,
id-MBSSessionFailedtoSetupList,
id-MBSSessionFailedtoSetuporModifyList,
id-MBSSessionSetupResponseList,
id-MBSSessionSetuporModifyResponseList,
id-MBSSessionToReleaseList,
id-MBSSessionSetupRequestList,
id-MBSSessionSetuporModifyRequestList,
id-MDTConfiguration,
id-MicoAllPLMN,
id-NetworkInstance,
id-NGAPIESupportInformationRequestList,
id-NGAPIESupportInformationResponseList,
id-NID,
id-NR-CGI,
id-NRNTNTAIInformation,
id-NPN-MobilityInformation,
id-NPN-PagingAssistanceInformation,
id-NPN-Support,
id-NR-PagingeDRXInformation,
id-OldAssociatedQosFlowList-ULendmarkerexpected,
id-OnboardingSupport,
id-PagingAssisDataforCEcapabUE,
id-PagingCauseIndicationForVoiceService,
id-PDUSessionAggregateMaximumBitRate,
id-PduSessionExpectedUEActivityBehaviour,
id-PDUSessionPairID,
id-PDUSessionResourceFailedToSetupListCxtFail,
id-PDUSessionResourceReleaseResponseTransfer,
id-PDUSessionType,
id-PEIPSassistanceInformation,
id-PSCellInformation,
id-PNI-NPNBasedMDT,
id-PNI-NPN-AreaScopeofMDT,
id-QMCConfigInfo,
id-QosFlowAdditionalInfoList,
id-QosFlowAddOrModifyRequestList,
id-QosFlowFailedToSetupList,
id-QosFlowFeedbackList,
id-QosFlowParametersList,
id-QosFlowSetupRequestList,
id-QosFlowToReleaseList,
id-QosMonitoringRequest,
id-QosMonitoringReportingFrequency,
id-SNPN-CellBasedMDT,
id-SNPN-TAIBasedMDT,
id-SNPN-BasedMDT,
id-SuccessfulHandoverReportList,
id-SupportedUETypeList,
id-UEContextReferenceAtSource,
id-RAT-Information,
id-RedundantCommonNetworkInstance,
id-RedundantDL-NGU-TNLInformationReused,
id-RedundantDL-NGU-UP-TNLInformation,
id-RedundantDLQosFlowPerTNLInformation,
id-RedundantPDUSessionInformation,
id-RedundantQosFlowIndicator,
id-RedundantUL-NGU-UP-TNLInformation,
id-SCTP-TLAs,
id-SecondaryRATUsageInformation,
id-SecurityIndication,
id-SecurityResult,
id-SgNB-UE-X2AP-ID,
id-S-NSSAI,
id-SONInformationReport,
id-SourceNodeID,
id-SourceNodeTNLAddrInfo,
id-SourceSN-to-TargetSN-QMCInfo,
id-SourceTNLAddrInfo,
id-SurvivalTime,
id-Selected-Target-SNPN-Identity,
id-TNLAssociationTransportLayerAddressNGRAN,
id-TAIMBSSupportList,
id-TAINSAGSupportList,
id-TargetHomeENB-ID,
id-TargetRNC-ID,
id-TimeBasedHandoverInformation,
id-TraceCollectionEntityURI,
id-TSCTrafficCharacteristics,
id-UEHistoryInformationFromTheUE,
id-UERadioCapabilityForPaging,
id-UERadioCapabilityForPagingOfNB-IoT,
id-UL-NGU-UP-TNLInformation,
id-UL-NGU-UP-TNLModifyList,
id-ULForwarding,
id-ULForwardingUP-TNLInformation,
id-UplinkTLContainer,
id-UsedRSNInformation,
id-UserLocationInformationTNGF,
id-UserLocationInformationTWIF,
id-UserLocationInformationW-AGF,
id-UserPlaneErrorIndicator,
id-EarlyMeasurement,
id-BeamMeasurementsReportConfiguration,
id-DLDiscarding,
id-TAI,
id-HFCNode-ID-new,
id-GlobalCable-ID-new,
id-FiveGProSeLayer2Multipath,
id-CandidateRelayUEInformationList,
id-FiveGProSeLayer2UEtoUERelay,
id-FiveGProSeLayer2UEtoUERemote,
id-SuccessfulPSCellChangeReportList,
id-TargetCellCRNTI,
id-TimeSinceFailure,
id-ClockQualityReportingControlInfo,
id-RANfeedbacktype,
id-QoSFlowTSCList,
id-TSCTrafficCharacteristicsFeedback,
id-ANPacketDelayBudgetUL,
id-CommServiceType,
id-MobileIAB-MTUserLocationInformation,
id-PDUsetQoSParameters,
id-PDUSetbasedHandlingIndicator,
id-N6JitterInformation,
id-ECNMarkingorCongestionInformationReportingRequest,
id-ECNMarkingorCongestionInformationReportingStatus,
id-MN-only-MDT-collection,
id-XrDeviceWith2Rx,
id-MaximumDataBurstVolume,
id-MBS-NGUFailureIndication,
id-UserPlaneFailureIndication,
id-UserPlaneFailureIndicationReport,
id-QoERVQoEReportingPaths,
id-UserLocationInformationN3IWF-without-PortNumber,
id-ExtendedBackupAMFName,
maxnoofAllowedAreas,
maxnoofAllowedCAGsperPLMN,
maxnoofAllowedS-NSSAIs,
maxnoofAoIMinusOne,
maxnoofBluetoothName,
maxnoofBPLMNs,
maxnoofCAGforMDT,
maxnoofCAGSperCell,
maxnoofCandidateCells,
maxnoofCellIDforMDT,
maxnoofCellIDforQMC,
maxnoofCellIDforWarning,
maxnoofCellinAoI,
maxnoofCellinEAI,
maxnoofCellsforMBS,
maxnoofCellsingNB,
maxnoofCellsinngeNB,
maxnoofCellsinNGRANNode,
maxnoofCellinTAI,
maxnoofCellsinUEHistoryInfo,
maxnoofCellsUEMovingTrajectory,
maxnoofDRBs,
maxnoofEmergencyAreaID,
maxnoofEAIforRestart,
maxnoofEPLMNs,
maxnoofEPLMNsPlusOne,
maxnoofE-RABs,
maxnoofErrors,
maxnoofExtSliceItems,
maxnoofESNPNs,
maxnoofForbTACs,
maxnoofFreqforMDT,
maxnoofMBSFSAs,
maxnoofMBSQoSFlows,
maxnoofMBSServiceAreaInformation,
maxnoofMBSAreaSessionIDs,
maxnoofMBSSessions,
maxnoofMBSSessionsofUE,
maxnoofMDTPLMNs,
maxnoofMRBs,
maxnoofMultiConnectivity,
maxnoofMultiConnectivityMinusOne,
maxnoofNeighPCIforMDT,
maxnoofNGAPIESupportInfo,
maxnoofNGConnectionsToReset,
maxNRARFCN,
maxnoofNRCellBands,
maxnoofNSAGs,
maxnoofPagingAreas,
maxnoofPC5QoSFlows,
maxnoofPDUSessions,
maxnoofPLMNs,
maxnoofPLMNforQMC,
maxnoofQosFlows,
maxnoofQosParaSets,
maxnoofRANNodeinAoI,
maxnoofRecommendedCells,
maxnoofRecommendedRANNodes,
maxnoofAoI,
maxnoofPSCellsPerPrimaryCellinUEHistoryInfo,
maxnoofReportedCells,
maxnoofSensorName,
maxnoofServedGUAMIs,
maxnoofSliceItems,
maxnoofMDTSNPNs,
maxnoofSNSSAIforQMC,
maxnoofSuccessfulHOReports,
maxnoofTACs,
maxnoofTACsinNTN,
maxnoofTAforMDT,
maxnoofTAforQMC,
maxnoofTAIforInactive,
maxnoofSupportedTAIforMBS,
maxnoofTAIforMBS,
maxnoofTAIforPaging,
maxnoofTAIforRestart,
maxnoofTAIforWarning,
maxnoofTAIinAoI,
maxnoofTargetS-NSSAIs,
maxnoofTimePeriods,
maxnoofTNLAssociations,
maxnoofUEAppLayerMeas,
maxnoofUEsforPaging,
maxnoofUETypes,
maxnoofWLANName,
maxnoofXnExtTLAs,
maxnoofXnGTP-TLAs,
maxnoofXnTLAs,
maxnoofThresholdsForExcessPacketDelay,
maxnoofCandidateRelayUEs,
maxnoofSuccessfulPSCellChangeReports,
maxnoofCellsTSS,
maxnoofPeriodicities,
maxnoofPartiallyAllowedS-NSSAIs,
maxnoofRSPPQoSFlows
FROM NGAP-Constants
Criticality,
ProcedureCode,
ProtocolIE-ID,
TriggeringMessage
FROM NGAP-CommonDataTypes
ProtocolExtensionContainer{},
ProtocolIE-Container{},
NGAP-PROTOCOL-EXTENSION,
ProtocolIE-SingleContainer{},
NGAP-PROTOCOL-IES
FROM NGAP-Containers;
-- A
AdditionalDLUPTNLInformationForHOList ::= SEQUENCE (SIZE(1..maxnoofMultiConnectivityMinusOne)) OF AdditionalDLUPTNLInformationForHOItem
AdditionalDLUPTNLInformationForHOItem ::= SEQUENCE {
additionalDL-NGU-UP-TNLInformation UPTransportLayerInformation,
additionalQosFlowSetupResponseList QosFlowListWithDataForwarding,
additionalDLForwardingUPTNLInformation UPTransportLayerInformation OPTIONAL,
iE-Extensions ProtocolExtensionContainer { { AdditionalDLUPTNLInformationForHOItem-ExtIEs} } OPTIONAL,
...
}
AdditionalDLUPTNLInformationForHOItem-ExtIEs NGAP-PROTOCOL-EXTENSION ::= {
{ ID id-AdditionalRedundantDL-NGU-UP-TNLInformation CRITICALITY ignore EXTENSION UPTransportLayerInformation PRESENCE optional },
...
}
AdditionalQosFlowInformation ::= ENUMERATED {
more-likely,
...
}
AerialUEsubscriptionInformation ::= ENUMERATED {
allowed,
not-allowed,
...
}
A2X-PC5-FlowBitRates ::= SEQUENCE {
a2X-GuaranteedFlowBitRate BitRate,
a2X-MaximumFlowBitRate BitRate,
iE-Extensions ProtocolExtensionContainer { {A2X-PC5-FlowBitRates-ExtIEs} } OPTIONAL,
...
}
A2X-PC5-FlowBitRates-ExtIEs NGAP-PROTOCOL-EXTENSION ::= {
...
}
A2X-PC5-QoS-Flow-List ::= SEQUENCE (SIZE(1..maxnoofPC5QoSFlows)) OF A2X-PC5-QoS-Flow-Item
A2X-PC5-QoS-Flow-Item ::= SEQUENCE {
a2X-PQI INTEGER (0..255, ...),
a2X-PC5-FlowBitRates A2X-PC5-FlowBitRates OPTIONAL,
a2X-Range ENUMERATED {m50, m80, m180, m200,
m350, m400, m500, m700,
m1000, ...} OPTIONAL,
iE-Extensions ProtocolExtensionContainer { {A2X-PC5-QoS-Flow-Item-ExtIEs} } OPTIONAL,
...
}
A2X-PC5-QoS-Flow-Item-ExtIEs NGAP-PROTOCOL-EXTENSION ::= {
...
}
A2X-PC5-QoS-Parameters ::= SEQUENCE {
a2X-PC5-QoS-Flow-List A2X-PC5-QoS-Flow-List,
a2X-PC5-LinkAggregateBitRates BitRate OPTIONAL,
iE-Extensions ProtocolExtensionContainer { {A2X-PC5-QoS-Parameters-ExtIEs} } OPTIONAL,
...
}
A2X-PC5-QoS-Parameters-ExtIEs NGAP-PROTOCOL-EXTENSION ::= {
...
}
AdditionalCancelledlocationReportingReferenceIDList ::= SEQUENCE (SIZE(1.. maxnoofAoIMinusOne)) OF AdditionalCancelledlocationReportingReferenceIDItem
AdditionalCancelledlocationReportingReferenceIDItem ::= SEQUENCE {
locationReportingReferenceIDToBeCancelled LocationReportingReferenceID,
iE-Extensions ProtocolExtensionContainer { { AdditionalCancelledlocationReportingReferenceIDItem-ExtIEs} } OPTIONAL,
...
}
AdditionalCancelledlocationReportingReferenceIDItem-ExtIEs NGAP-PROTOCOL-EXTENSION ::= {
...
}
AllocationAndRetentionPriority ::= SEQUENCE {
priorityLevelARP PriorityLevelARP,
pre-emptionCapability Pre-emptionCapability,
pre-emptionVulnerability Pre-emptionVulnerability,
iE-Extensions ProtocolExtensionContainer { {AllocationAndRetentionPriority-ExtIEs} } OPTIONAL,
...
}
AllocationAndRetentionPriority-ExtIEs NGAP-PROTOCOL-EXTENSION ::= {
...
}
Allowed-CAG-List-per-PLMN ::= SEQUENCE (SIZE(1..maxnoofAllowedCAGsperPLMN)) OF CAG-ID
AllowedNSSAI ::= SEQUENCE (SIZE(1..maxnoofAllowedS-NSSAIs)) OF AllowedNSSAI-Item
AllowedNSSAI-Item ::= SEQUENCE {
s-NSSAI S-NSSAI,
iE-Extensions ProtocolExtensionContainer { {AllowedNSSAI-Item-ExtIEs} } OPTIONAL,
...
}
AllowedNSSAI-Item-ExtIEs NGAP-PROTOCOL-EXTENSION ::= {
...
}
Allowed-PNI-NPN-List ::= SEQUENCE (SIZE(1..maxnoofEPLMNsPlusOne)) OF Allowed-PNI-NPN-Item
Allowed-PNI-NPN-Item ::= SEQUENCE {
pLMNIdentity PLMNIdentity,
pNI-NPN-restricted ENUMERATED {restricted, not-restricted, ...},
allowed-CAG-List-per-PLMN Allowed-CAG-List-per-PLMN,
iE-Extensions ProtocolExtensionContainer { {Allowed-PNI-NPN-Item-ExtIEs} } OPTIONAL,
...
}
Allowed-PNI-NPN-Item-ExtIEs NGAP-PROTOCOL-EXTENSION ::= {
...
}
AllowedTACs ::= SEQUENCE (SIZE(1..maxnoofAllowedAreas)) OF TAC
AlternativeQoSParaSetIndex ::= INTEGER (1..8, ...)
AlternativeQoSParaSetNotifyIndex ::= INTEGER (0..8, ...)
AlternativeQoSParaSetList ::= SEQUENCE (SIZE(1..maxnoofQosParaSets)) OF AlternativeQoSParaSetItem
AlternativeQoSParaSetItem ::= SEQUENCE {
alternativeQoSParaSetIndex AlternativeQoSParaSetIndex,
guaranteedFlowBitRateDL BitRate OPTIONAL,
guaranteedFlowBitRateUL BitRate OPTIONAL,
packetDelayBudget PacketDelayBudget OPTIONAL,
packetErrorRate PacketErrorRate OPTIONAL,
iE-Extensions ProtocolExtensionContainer { {AlternativeQoSParaSetItem-ExtIEs} } OPTIONAL,
...
}
AlternativeQoSParaSetItem-ExtIEs NGAP-PROTOCOL-EXTENSION ::= {
{ ID id-MaximumDataBurstVolume CRITICALITY ignore EXTENSION MaximumDataBurstVolume PRESENCE optional },
...
}
AssistanceInformationQoE-Meas ::= INTEGER (1..16, ...)
AMFName ::= PrintableString (SIZE(1..150, ...))
AMFNameVisibleString ::= VisibleString (SIZE(1..150, ...))
AMFNameUTF8String ::= UTF8String (SIZE(1..150, ...))
AMFPagingTarget ::= CHOICE {
globalRANNodeID GlobalRANNodeID,
tAI TAI,
choice-Extensions ProtocolIE-SingleContainer { {AMFPagingTarget-ExtIEs} }
}
AMFPagingTarget-ExtIEs NGAP-PROTOCOL-IES ::= {
...
}
AMFPointer ::= BIT STRING (SIZE(6))
AMFRegionID ::= BIT STRING (SIZE(8))
AMFSetID ::= BIT STRING (SIZE(10))
AMF-TNLAssociationSetupList ::= SEQUENCE (SIZE(1..maxnoofTNLAssociations)) OF AMF-TNLAssociationSetupItem
AMF-TNLAssociationSetupItem ::= SEQUENCE {
aMF-TNLAssociationAddress CPTransportLayerInformation,
iE-Extensions ProtocolExtensionContainer { {AMF-TNLAssociationSetupItem-ExtIEs} } OPTIONAL,
...
}
AMF-TNLAssociationSetupItem-ExtIEs NGAP-PROTOCOL-EXTENSION ::= {
...
}
AMF-TNLAssociationToAddList ::= SEQUENCE (SIZE(1..maxnoofTNLAssociations)) OF AMF-TNLAssociationToAddItem
AMF-TNLAssociationToAddItem ::= SEQUENCE {
aMF-TNLAssociationAddress CPTransportLayerInformation,
tNLAssociationUsage TNLAssociationUsage OPTIONAL,
tNLAddressWeightFactor TNLAddressWeightFactor,
iE-Extensions ProtocolExtensionContainer { {AMF-TNLAssociationToAddItem-ExtIEs} } OPTIONAL,
...
}
AMF-TNLAssociationToAddItem-ExtIEs NGAP-PROTOCOL-EXTENSION ::= {
...
}
AMF-TNLAssociationToRemoveList ::= SEQUENCE (SIZE(1..maxnoofTNLAssociations)) OF AMF-TNLAssociationToRemoveItem
AMF-TNLAssociationToRemoveItem ::= SEQUENCE {
aMF-TNLAssociationAddress CPTransportLayerInformation,
iE-Extensions ProtocolExtensionContainer { {AMF-TNLAssociationToRemoveItem-ExtIEs} } OPTIONAL,
...
}
AMF-TNLAssociationToRemoveItem-ExtIEs NGAP-PROTOCOL-EXTENSION ::= {
{ID id-TNLAssociationTransportLayerAddressNGRAN CRITICALITY reject EXTENSION CPTransportLayerInformation PRESENCE optional},
...
}
AMF-TNLAssociationToUpdateList ::= SEQUENCE (SIZE(1..maxnoofTNLAssociations)) OF AMF-TNLAssociationToUpdateItem
AMF-TNLAssociationToUpdateItem ::= SEQUENCE {
aMF-TNLAssociationAddress CPTransportLayerInformation,
tNLAssociationUsage TNLAssociationUsage OPTIONAL,
tNLAddressWeightFactor TNLAddressWeightFactor OPTIONAL,
iE-Extensions ProtocolExtensionContainer { {AMF-TNLAssociationToUpdateItem-ExtIEs} } OPTIONAL,
...
}
AMF-TNLAssociationToUpdateItem-ExtIEs NGAP-PROTOCOL-EXTENSION ::= {
...
}
AMF-UE-NGAP-ID ::= INTEGER (0..1099511627775)
AreaOfInterest ::= SEQUENCE {
areaOfInterestTAIList AreaOfInterestTAIList OPTIONAL,
areaOfInterestCellList AreaOfInterestCellList OPTIONAL,
areaOfInterestRANNodeList AreaOfInterestRANNodeList OPTIONAL,
iE-Extensions ProtocolExtensionContainer { {AreaOfInterest-ExtIEs} } OPTIONAL,
...
}
AreaOfInterest-ExtIEs NGAP-PROTOCOL-EXTENSION ::= {
...
}
AreaOfInterestCellList ::= SEQUENCE (SIZE(1..maxnoofCellinAoI)) OF AreaOfInterestCellItem
AreaOfInterestCellItem ::= SEQUENCE {
nGRAN-CGI NGRAN-CGI,
iE-Extensions ProtocolExtensionContainer { {AreaOfInterestCellItem-ExtIEs} } OPTIONAL,
...
}
AreaOfInterestCellItem-ExtIEs NGAP-PROTOCOL-EXTENSION ::= {
...
}
AreaOfInterestList ::= SEQUENCE (SIZE(1..maxnoofAoI)) OF AreaOfInterestItem
AreaOfInterestItem ::= SEQUENCE {
areaOfInterest AreaOfInterest,
locationReportingReferenceID LocationReportingReferenceID,
iE-Extensions ProtocolExtensionContainer { {AreaOfInterestItem-ExtIEs} } OPTIONAL,
...
}
AreaOfInterestItem-ExtIEs NGAP-PROTOCOL-EXTENSION ::= {
...
}
AreaOfInterestRANNodeList ::= SEQUENCE (SIZE(1..maxnoofRANNodeinAoI)) OF AreaOfInterestRANNodeItem
AreaOfInterestRANNodeItem ::= SEQUENCE {
globalRANNodeID GlobalRANNodeID,
iE-Extensions ProtocolExtensionContainer { {AreaOfInterestRANNodeItem-ExtIEs} } OPTIONAL,
...
}
AreaOfInterestRANNodeItem-ExtIEs NGAP-PROTOCOL-EXTENSION ::= {
...
}
AreaOfInterestTAIList ::= SEQUENCE (SIZE(1..maxnoofTAIinAoI)) OF AreaOfInterestTAIItem
AreaOfInterestTAIItem ::= SEQUENCE {
tAI TAI,
iE-Extensions ProtocolExtensionContainer { {AreaOfInterestTAIItem-ExtIEs} } OPTIONAL,
...
}
AreaOfInterestTAIItem-ExtIEs NGAP-PROTOCOL-EXTENSION ::= {
...
}
AssistanceDataForPaging ::= SEQUENCE {
assistanceDataForRecommendedCells AssistanceDataForRecommendedCells OPTIONAL,
pagingAttemptInformation PagingAttemptInformation OPTIONAL,
iE-Extensions ProtocolExtensionContainer { {AssistanceDataForPaging-ExtIEs} } OPTIONAL,
...
}
AssistanceDataForPaging-ExtIEs NGAP-PROTOCOL-EXTENSION ::= {
{ ID id-NPN-PagingAssistanceInformation CRITICALITY ignore EXTENSION NPN-PagingAssistanceInformation PRESENCE optional }|
{ ID id-PagingAssisDataforCEcapabUE CRITICALITY ignore EXTENSION PagingAssisDataforCEcapabUE PRESENCE optional },
...
}
AssistanceDataForRecommendedCells ::= SEQUENCE {
recommendedCellsForPaging RecommendedCellsForPaging,
iE-Extensions ProtocolExtensionContainer { {AssistanceDataForRecommendedCells-ExtIEs} } OPTIONAL,
...
}
AssistanceDataForRecommendedCells-ExtIEs NGAP-PROTOCOL-EXTENSION ::= {
...
}
AssociatedMBSQosFlowSetupRequestList ::= SEQUENCE (SIZE(1..maxnoofMBSQoSFlows)) OF AssociatedMBSQosFlowSetupRequestItem
AssociatedMBSQosFlowSetupRequestItem ::= SEQUENCE {
mBS-QosFlowIdentifier QosFlowIdentifier,
associatedUnicastQosFlowIdentifier QosFlowIdentifier,
iE-Extensions ProtocolExtensionContainer { { AssociatedMBSQosFlowSetupRequestItem-ExtIEs} } OPTIONAL,
...
}
AssociatedMBSQosFlowSetupRequestItem-ExtIEs NGAP-PROTOCOL-EXTENSION ::= {
...
}
AssociatedMBSQosFlowSetuporModifyRequestList ::= SEQUENCE (SIZE(1..maxnoofMBSQoSFlows)) OF AssociatedMBSQosFlowSetuporModifyRequestItem
AssociatedMBSQosFlowSetuporModifyRequestItem ::= SEQUENCE {
mBS-QosFlowIdentifier QosFlowIdentifier,
associatedUnicastQosFlowIdentifier QosFlowIdentifier,
iE-Extensions ProtocolExtensionContainer { { AssociatedMBSQosFlowSetuporModifyRequestItem-ExtIEs} } OPTIONAL,
...
}
AssociatedMBSQosFlowSetuporModifyRequestItem-ExtIEs NGAP-PROTOCOL-EXTENSION ::= {
...
}
AssociatedQosFlowList ::= SEQUENCE (SIZE(1..maxnoofQosFlows)) OF AssociatedQosFlowItem
AssociatedQosFlowItem ::= SEQUENCE {
qosFlowIdentifier QosFlowIdentifier,
qosFlowMappingIndication ENUMERATED {ul, dl, ...} OPTIONAL,
iE-Extensions ProtocolExtensionContainer { {AssociatedQosFlowItem-ExtIEs} } OPTIONAL,
...
}
AssociatedQosFlowItem-ExtIEs NGAP-PROTOCOL-EXTENSION ::= {
{ ID id-CurrentQoSParaSetIndex CRITICALITY ignore EXTENSION AlternativeQoSParaSetIndex PRESENCE optional },
...
}
AssociatedSessionID ::= OCTET STRING
AUN3DeviceAccessInfo ::= SEQUENCE {
aUN3DeviceAccess ENUMERATED {true, ...},
existingNGConnectionwithSameLocation ENUMERATED {true, false, ...},
iE-Extensions ProtocolExtensionContainer { { AUN3DeviceAccessInfo-ExtIEs} } OPTIONAL,
...
}
AUN3DeviceAccessInfo-ExtIEs NGAP-PROTOCOL-EXTENSION ::= {
...
}
AuthenticatedIndication ::= ENUMERATED {true, ...}
AveragingWindow ::= INTEGER (0..4095, ...)
AreaScopeOfMDT-NR ::= CHOICE {
cellBased CellBasedMDT-NR,
tABased TABasedMDT,
pLMNWide NULL,
tAIBased TAIBasedMDT,
choice-Extensions ProtocolIE-SingleContainer { {AreaScopeOfMDT-NR-ExtIEs} }
}
AreaScopeOfMDT-NR-ExtIEs NGAP-PROTOCOL-IES ::= {
{ ID id-PNI-NPNBasedMDT CRITICALITY ignore TYPE PNI-NPNBasedMDT PRESENCE mandatory }|
{ ID id-SNPN-CellBasedMDT CRITICALITY ignore TYPE SNPN-CellBasedMDT PRESENCE mandatory }|
{ ID id-SNPN-TAIBasedMDT CRITICALITY ignore TYPE SNPN-TAIBasedMDT PRESENCE mandatory }|
{ ID id-SNPN-BasedMDT CRITICALITY ignore TYPE SNPN-BasedMDT PRESENCE mandatory },
...
}
AreaScopeOfMDT-EUTRA ::= CHOICE {
cellBased CellBasedMDT-EUTRA,
tABased TABasedMDT,
pLMNWide NULL,
tAIBased TAIBasedMDT,
choice-Extensions ProtocolIE-SingleContainer { {AreaScopeOfMDT-EUTRA-ExtIEs} }
}
AreaScopeOfMDT-EUTRA-ExtIEs NGAP-PROTOCOL-IES ::= {
...
}
AreaScopeOfNeighCellsList ::= SEQUENCE (SIZE(1..maxnoofFreqforMDT)) OF AreaScopeOfNeighCellsItem
AreaScopeOfNeighCellsItem ::= SEQUENCE {
nrFrequencyInfo NRFrequencyInfo,
pciListForMDT PCIListForMDT OPTIONAL,
iE-Extensions ProtocolExtensionContainer { { AreaScopeOfNeighCellsItem-ExtIEs} } OPTIONAL,
...
}
AreaScopeOfNeighCellsItem-ExtIEs NGAP-PROTOCOL-EXTENSION ::= {
...
}
AreaScopeOfQMC ::= CHOICE {
cellBased CellBasedQMC,
tABased TABasedQMC,
tAIBased TAIBasedQMC,
pLMNAreaBased PLMNAreaBasedQMC,
choice-Extensions ProtocolIE-SingleContainer { { AreaScopeOfQMC-ExtIEs} }
}
AreaScopeOfQMC-ExtIEs NGAP-PROTOCOL-IES ::= {
...
}
AvailableRANVisibleQoEMetrics ::= SEQUENCE {
applicationLayerBufferLevelList ENUMERATED {true, ...} OPTIONAL,
playoutDelayForMediaStartup ENUMERATED {true, ...} OPTIONAL,
iE-Extensions ProtocolExtensionContainer { { AvailableRANVisibleQoEMetrics-ExtIEs} } OPTIONAL,
...
}
AvailableRANVisibleQoEMetrics-ExtIEs NGAP-PROTOCOL-EXTENSION ::= {
...
}
-- B
BeamMeasurementsReportConfiguration ::= SEQUENCE {
beamMeasurementsReportQuantity BeamMeasurementsReportQuantity OPTIONAL,
maxNrofRS-IndexesToReport MaxNrofRS-IndexesToReport OPTIONAL,
iE-Extensions ProtocolExtensionContainer { { BeamMeasurementsReportConfiguration-ExtIEs} } OPTIONAL,
...
}
BeamMeasurementsReportConfiguration-ExtIEs NGAP-PROTOCOL-EXTENSION ::= {
...
}
BeamMeasurementsReportQuantity ::= SEQUENCE {
rSRP ENUMERATED {true, ..., false},
rSRQ ENUMERATED {true, ..., false},
sINR ENUMERATED {true, ..., false},
iE-Extensions ProtocolExtensionContainer { { BeamMeasurementsReportQuantity-ExtIEs} } OPTIONAL,
...
}
BeamMeasurementsReportQuantity-ExtIEs NGAP-PROTOCOL-EXTENSION ::= {
...
}
BitRate ::= INTEGER (0..4000000000000, ...)
BroadcastCancelledAreaList ::= CHOICE {
cellIDCancelledEUTRA CellIDCancelledEUTRA,
tAICancelledEUTRA TAICancelledEUTRA,
emergencyAreaIDCancelledEUTRA EmergencyAreaIDCancelledEUTRA,
cellIDCancelledNR CellIDCancelledNR,
tAICancelledNR TAICancelledNR,
emergencyAreaIDCancelledNR EmergencyAreaIDCancelledNR,
choice-Extensions ProtocolIE-SingleContainer { {BroadcastCancelledAreaList-ExtIEs} }
}
BroadcastCancelledAreaList-ExtIEs NGAP-PROTOCOL-IES ::= {
...
}
BroadcastCompletedAreaList ::= CHOICE {
cellIDBroadcastEUTRA CellIDBroadcastEUTRA,
tAIBroadcastEUTRA TAIBroadcastEUTRA,
emergencyAreaIDBroadcastEUTRA EmergencyAreaIDBroadcastEUTRA,
cellIDBroadcastNR CellIDBroadcastNR,
tAIBroadcastNR TAIBroadcastNR,
emergencyAreaIDBroadcastNR EmergencyAreaIDBroadcastNR,
choice-Extensions ProtocolIE-SingleContainer { {BroadcastCompletedAreaList-ExtIEs} }
}
BroadcastCompletedAreaList-ExtIEs NGAP-PROTOCOL-IES ::= {
...
}
BroadcastPLMNList ::= SEQUENCE (SIZE(1..maxnoofBPLMNs)) OF BroadcastPLMNItem
BroadcastPLMNItem ::= SEQUENCE {
pLMNIdentity PLMNIdentity,
tAISliceSupportList SliceSupportList,
iE-Extensions ProtocolExtensionContainer { {BroadcastPLMNItem-ExtIEs} } OPTIONAL,
...
}
BroadcastPLMNItem-ExtIEs NGAP-PROTOCOL-EXTENSION ::= {
{ID id-NPN-Support CRITICALITY reject EXTENSION NPN-Support PRESENCE optional}|
{ID id-ExtendedTAISliceSupportList CRITICALITY reject EXTENSION ExtendedSliceSupportList PRESENCE optional}|
{ID id-TAINSAGSupportList CRITICALITY ignore EXTENSION TAINSAGSupportList PRESENCE optional},
...
}
BroadcastTransportFailureTransfer ::= SEQUENCE {
mBS-SessionID MBS-SessionID,
cause Cause,
criticalityDiagnostics CriticalityDiagnostics OPTIONAL,
iE-Extensions ProtocolExtensionContainer { { BroadcastTransportFailureTransfer-ExtIEs} } OPTIONAL,
...
}
BroadcastTransportFailureTransfer-ExtIEs NGAP-PROTOCOL-EXTENSION ::= {
...
}
BroadcastTransportRequestTransfer ::= SEQUENCE {
mBS-SessionID MBS-SessionID,
mBS-SessionTNLInfoNGRAN MBS-SessionTNLInfoNGRAN,
iE-Extensions ProtocolExtensionContainer { {BroadcastTransportRequestTransfer-ExtIEs} } OPTIONAL,
...
}
BroadcastTransportRequestTransfer-ExtIEs NGAP-PROTOCOL-EXTENSION ::= {
...
}
BroadcastTransportResponseTransfer ::= SEQUENCE {
mBS-SessionID MBS-SessionID,
iE-Extensions ProtocolExtensionContainer { {BroadcastTransportResponseTransfer-ExtIEs} } OPTIONAL,
...
}
BroadcastTransportResponseTransfer-ExtIEs NGAP-PROTOCOL-EXTENSION ::= {
...
}
BluetoothMeasurementConfiguration ::= SEQUENCE {
bluetoothMeasConfig BluetoothMeasConfig,
bluetoothMeasConfigNameList BluetoothMeasConfigNameList OPTIONAL,
bt-rssi ENUMERATED {true, ...} OPTIONAL,
iE-Extensions ProtocolExtensionContainer { { BluetoothMeasurementConfiguration-ExtIEs } } OPTIONAL,
...
}
BluetoothMeasurementConfiguration-ExtIEs NGAP-PROTOCOL-EXTENSION ::= {
...
}
BluetoothMeasConfigNameList ::= SEQUENCE (SIZE(1..maxnoofBluetoothName)) OF BluetoothMeasConfigNameItem
BluetoothMeasConfigNameItem ::= SEQUENCE {
bluetoothName BluetoothName,
iE-Extensions ProtocolExtensionContainer { { BluetoothMeasConfigNameItem-ExtIEs } } OPTIONAL,
...
}
BluetoothMeasConfigNameItem-ExtIEs NGAP-PROTOCOL-EXTENSION ::= {
...
}
BluetoothMeasConfig::= ENUMERATED {setup,...}
BluetoothName ::= OCTET STRING (SIZE (1..248))
BurstArrivalTime ::= OCTET STRING
BurstArrivalTimeWindow ::= SEQUENCE {
burstArrivalTimeWindowStart INTEGER (0..640000, ...),
burstArrivalTimeWindowEnd INTEGER (0..640000, ...),
iE-Extension ProtocolExtensionContainer { {BurstArrivalTimeWindow-ExtIEs} } OPTIONAL,
...
}
BurstArrivalTimeWindow-ExtIEs NGAP-PROTOCOL-EXTENSION ::= {
...
}
-- C
CAG-ID ::= BIT STRING (SIZE(32))
CandidateRelayUEInformationList ::= SEQUENCE (SIZE(1.. maxnoofCandidateRelayUEs)) OF CandidateRelayUEInformationItem
CandidateRelayUEInformationItem ::= SEQUENCE {
candidateRelayUE-Id CandidateRelayUE-ID,
iE-Extensions ProtocolExtensionContainer { { CandidateRelayUEInformationItem-ExtIEs} } OPTIONAL,
...
}
CandidateRelayUEInformationItem-ExtIEs NGAP-PROTOCOL-EXTENSION ::= {
...
}
CandidateRelayUE-ID ::= BIT STRING (SIZE(24))
CancelAllWarningMessages ::= ENUMERATED {
true,
...
}
CancelledCellsInEAI-EUTRA ::= SEQUENCE (SIZE(1..maxnoofCellinEAI)) OF CancelledCellsInEAI-EUTRA-Item
CancelledCellsInEAI-EUTRA-Item ::= SEQUENCE {
eUTRA-CGI EUTRA-CGI,
numberOfBroadcasts NumberOfBroadcasts,
iE-Extensions ProtocolExtensionContainer { {CancelledCellsInEAI-EUTRA-Item-ExtIEs} } OPTIONAL,
...
}
CancelledCellsInEAI-EUTRA-Item-ExtIEs NGAP-PROTOCOL-EXTENSION ::= {
...
}
CancelledCellsInEAI-NR ::= SEQUENCE (SIZE(1..maxnoofCellinEAI)) OF CancelledCellsInEAI-NR-Item
CancelledCellsInEAI-NR-Item ::= SEQUENCE {
nR-CGI NR-CGI,
numberOfBroadcasts NumberOfBroadcasts,
iE-Extensions ProtocolExtensionContainer { {CancelledCellsInEAI-NR-Item-ExtIEs} } OPTIONAL,
...
}
CancelledCellsInEAI-NR-Item-ExtIEs NGAP-PROTOCOL-EXTENSION ::= {
...
}
CancelledCellsInTAI-EUTRA ::= SEQUENCE (SIZE(1..maxnoofCellinTAI)) OF CancelledCellsInTAI-EUTRA-Item
CancelledCellsInTAI-EUTRA-Item ::= SEQUENCE {
eUTRA-CGI EUTRA-CGI,
numberOfBroadcasts NumberOfBroadcasts,
iE-Extensions ProtocolExtensionContainer { {CancelledCellsInTAI-EUTRA-Item-ExtIEs} } OPTIONAL,
...
}
CancelledCellsInTAI-EUTRA-Item-ExtIEs NGAP-PROTOCOL-EXTENSION ::= {
...
}
CancelledCellsInTAI-NR ::= SEQUENCE (SIZE(1..maxnoofCellinTAI)) OF CancelledCellsInTAI-NR-Item
CancelledCellsInTAI-NR-Item ::= SEQUENCE{
nR-CGI NR-CGI,
numberOfBroadcasts NumberOfBroadcasts,
iE-Extensions ProtocolExtensionContainer { {CancelledCellsInTAI-NR-Item-ExtIEs} } OPTIONAL,
...
}
CancelledCellsInTAI-NR-Item-ExtIEs NGAP-PROTOCOL-EXTENSION ::= {
...
}
CandidateCellList ::= SEQUENCE (SIZE(1.. maxnoofCandidateCells)) OF CandidateCellItem
CandidateCellItem ::= SEQUENCE{
candidateCell CandidateCell,
iE-Extensions ProtocolExtensionContainer { {CandidateCellItem-ExtIEs} } OPTIONAL,
...
}
CandidateCellItem-ExtIEs NGAP-PROTOCOL-EXTENSION ::= {
...
}
CandidateCell::= CHOICE {
candidateCGI CandidateCellID,
candidatePCI CandidatePCI,
choice-Extensions ProtocolIE-SingleContainer { { CandidateCell-ExtIEs} }
}
CandidateCell-ExtIEs NGAP-PROTOCOL-IES ::= {
...
}
CandidateCellID::= SEQUENCE {
candidateCellID NR-CGI,
iE-Extensions ProtocolExtensionContainer { { CandidateCellID-ExtIEs} } OPTIONAL,
...
}
CandidateCellID-ExtIEs NGAP-PROTOCOL-EXTENSION ::= {
...
}
CandidatePCI::= SEQUENCE {
candidatePCI INTEGER (0..1007, ...),
candidateNRARFCN INTEGER (0..maxNRARFCN),
iE-Extensions ProtocolExtensionContainer { { CandidatePCI-ExtIEs} } OPTIONAL,
...
}
CandidatePCI-ExtIEs NGAP-PROTOCOL-EXTENSION ::= {
...
}
Cause ::= CHOICE {
radioNetwork CauseRadioNetwork,
transport CauseTransport,
nas CauseNas,
protocol CauseProtocol,
misc CauseMisc,
choice-Extensions ProtocolIE-SingleContainer { {Cause-ExtIEs} }
}
Cause-ExtIEs NGAP-PROTOCOL-IES ::= {
...
}
CauseMisc ::= ENUMERATED {
control-processing-overload,
not-enough-user-plane-processing-resources,
hardware-failure,
om-intervention,
unknown-PLMN-or-SNPN,
unspecified,
...
}
CauseNas ::= ENUMERATED {
normal-release,
authentication-failure,
deregister,
unspecified,
...,
uE-not-in-PLMN-serving-area,
mobile-IAB-not-authorized,
iAB-not-authorized
}
CauseProtocol ::= ENUMERATED {
transfer-syntax-error,
abstract-syntax-error-reject,
abstract-syntax-error-ignore-and-notify,
message-not-compatible-with-receiver-state,
semantic-error,
abstract-syntax-error-falsely-constructed-message,
unspecified,
...
}
CauseRadioNetwork ::= ENUMERATED {
unspecified,
txnrelocoverall-expiry,
successful-handover,
release-due-to-ngran-generated-reason,
release-due-to-5gc-generated-reason,
handover-cancelled,
partial-handover,
ho-failure-in-target-5GC-ngran-node-or-target-system,
ho-target-not-allowed,
tngrelocoverall-expiry,
tngrelocprep-expiry,
cell-not-available,
unknown-targetID,
no-radio-resources-available-in-target-cell,
unknown-local-UE-NGAP-ID,
inconsistent-remote-UE-NGAP-ID,
handover-desirable-for-radio-reason,
time-critical-handover,
resource-optimisation-handover,
reduce-load-in-serving-cell,
user-inactivity,
radio-connection-with-ue-lost,
radio-resources-not-available,
invalid-qos-combination,
failure-in-radio-interface-procedure,
interaction-with-other-procedure,
unknown-PDU-session-ID,
unkown-qos-flow-ID,
multiple-PDU-session-ID-instances,
multiple-qos-flow-ID-instances,
encryption-and-or-integrity-protection-algorithms-not-supported,
ng-intra-system-handover-triggered,
ng-inter-system-handover-triggered,
xn-handover-triggered,
not-supported-5QI-value,
ue-context-transfer,
ims-voice-eps-fallback-or-rat-fallback-triggered,
up-integrity-protection-not-possible,
up-confidentiality-protection-not-possible,
slice-not-supported,
ue-in-rrc-inactive-state-not-reachable,
redirection,
resources-not-available-for-the-slice,
ue-max-integrity-protected-data-rate-reason,
release-due-to-cn-detected-mobility,
...,
n26-interface-not-available,
release-due-to-pre-emption,
multiple-location-reporting-reference-ID-instances,
rsn-not-available-for-the-up,
npn-access-denied,
cag-only-access-denied,
insufficient-ue-capabilities,
redcap-ue-not-supported,
unknown-MBS-Session-ID,
indicated-MBS-session-area-information-not-served-by-the-gNB,
inconsistent-slice-info-for-the-session,
misaligned-association-for-multicast-unicast,
eredcap-ue-not-supported,
two-rx-xr-ue-not-supported
}
CauseTransport ::= ENUMERATED {
transport-resource-unavailable,
unspecified,
...
}
Cell-CAGInformation ::= SEQUENCE {
nGRAN-CGI NGRAN-CGI,
cellCAGList CellCAGList,
iE-Extensions ProtocolExtensionContainer { {Cell-CAGInformation-ExtIEs} } OPTIONAL,
...
}
Cell-CAGInformation-ExtIEs NGAP-PROTOCOL-EXTENSION ::= {
...
}
CellCAGList ::= SEQUENCE (SIZE(1..maxnoofCAGSperCell)) OF CAG-ID
CellIDBroadcastEUTRA ::= SEQUENCE (SIZE(1..maxnoofCellIDforWarning)) OF CellIDBroadcastEUTRA-Item
CellIDBroadcastEUTRA-Item ::= SEQUENCE {
eUTRA-CGI EUTRA-CGI,
iE-Extensions ProtocolExtensionContainer { {CellIDBroadcastEUTRA-Item-ExtIEs} } OPTIONAL,
...
}
CellIDBroadcastEUTRA-Item-ExtIEs NGAP-PROTOCOL-EXTENSION ::= {
...
}
CellIDBroadcastNR ::= SEQUENCE (SIZE(1..maxnoofCellIDforWarning)) OF CellIDBroadcastNR-Item
CellIDBroadcastNR-Item ::= SEQUENCE {
nR-CGI NR-CGI,
iE-Extensions ProtocolExtensionContainer { {CellIDBroadcastNR-Item-ExtIEs} } OPTIONAL,
...
}
CellIDBroadcastNR-Item-ExtIEs NGAP-PROTOCOL-EXTENSION ::= {
...
}
CellIDCancelledEUTRA ::= SEQUENCE (SIZE(1..maxnoofCellIDforWarning)) OF CellIDCancelledEUTRA-Item
CellIDCancelledEUTRA-Item ::= SEQUENCE {
eUTRA-CGI EUTRA-CGI,
numberOfBroadcasts NumberOfBroadcasts,
iE-Extensions ProtocolExtensionContainer { {CellIDCancelledEUTRA-Item-ExtIEs} } OPTIONAL,
...
}
CellIDCancelledEUTRA-Item-ExtIEs NGAP-PROTOCOL-EXTENSION ::= {
...
}
CellIDCancelledNR ::= SEQUENCE (SIZE(1..maxnoofCellIDforWarning)) OF CellIDCancelledNR-Item
CellIDCancelledNR-Item ::= SEQUENCE {
nR-CGI NR-CGI,
numberOfBroadcasts NumberOfBroadcasts,
iE-Extensions ProtocolExtensionContainer { {CellIDCancelledNR-Item-ExtIEs} } OPTIONAL,
...
}
CellIDCancelledNR-Item-ExtIEs NGAP-PROTOCOL-EXTENSION ::= {
...
}
CellIDListForRestart ::= CHOICE {
eUTRA-CGIListforRestart EUTRA-CGIList,
nR-CGIListforRestart NR-CGIList,
choice-Extensions ProtocolIE-SingleContainer { {CellIDListForRestart-ExtIEs} }
}
CellIDListForRestart-ExtIEs NGAP-PROTOCOL-IES ::= {
...
}
CellSize ::= ENUMERATED {verysmall, small, medium, large, ...}
CellType ::= SEQUENCE {
cellSize CellSize,
iE-Extensions ProtocolExtensionContainer { {CellType-ExtIEs} } OPTIONAL,
...
}
CellType-ExtIEs NGAP-PROTOCOL-EXTENSION ::= {
...
}
CEmodeBSupport-Indicator ::= ENUMERATED {supported,...}
CEmodeBrestricted ::= ENUMERATED {
restricted,
not-restricted,
...
}
ClockAccuracy ::= CHOICE {
clockAccuracyValue INTEGER (1..40000000, ...),
clockAccuracyIndex INTEGER (32..47, ...),
choice-Extensions ProtocolIE-SingleContainer { { ClockAccuracy-ExtIEs} }
}
ClockAccuracy-ExtIEs NGAP-PROTOCOL-IES ::= {
...
}
ClockQualityAcceptanceIndication ::= SEQUENCE {
clockQualityAcceptanceCriteria ClockQualityAcceptanceCriteria,
iE-Extensions ProtocolExtensionContainer { {ClockQualityAcceptanceIndication-ExtIEs} } OPTIONAL,
...
}
ClockQualityAcceptanceIndication-ExtIEs NGAP-PROTOCOL-EXTENSION ::= {
...
}
ClockQualityAcceptanceCriteria ::= SEQUENCE {
synchronisationState BIT STRING (SIZE(8, ...)) OPTIONAL,
traceabletoUTC ENUMERATED {true, ...} OPTIONAL,
traceabletoGNSS ENUMERATED {true, ...} OPTIONAL,
clockFrequencyStability BIT STRING (SIZE(16)) OPTIONAL,
clockAccuracy INTEGER (1..40000000, ...) OPTIONAL,
parentTImeSource BIT STRING (SIZE(16, ...)) OPTIONAL,
iE-Extensions ProtocolExtensionContainer { { ClockQualityAcceptanceCriteria-ExtIEs} } OPTIONAL,
...
}
ClockQualityAcceptanceCriteria-ExtIEs NGAP-PROTOCOL-EXTENSION ::= {
...
}
ClockQualityReportingControlInfo ::= SEQUENCE {
clockQualityDetailLevel ClockQualityDetailLevel,
iE-Extensions ProtocolExtensionContainer { {ClockQualityReportingControlInfo-ExtIEs} } OPTIONAL,
...
}
ClockQualityReportingControlInfo-ExtIEs NGAP-PROTOCOL-EXTENSION ::= {
...
}
ClockQualityDetailLevel ::= CHOICE {
clockQualityMetrics NULL,
clockQualityAcceptanceIndication ClockQualityAcceptanceIndication,
choice-extensions ProtocolIE-SingleContainer { {ClockQualityDetailLevel-ExtIEs} }
}
ClockQualityDetailLevel-ExtIEs NGAP-PROTOCOL-IES ::= {
...
}
CNAssistedRANTuning ::= SEQUENCE {
expectedUEBehaviour ExpectedUEBehaviour OPTIONAL,
iE-Extensions ProtocolExtensionContainer { {CNAssistedRANTuning-ExtIEs} } OPTIONAL,
...
}
CNAssistedRANTuning-ExtIEs NGAP-PROTOCOL-EXTENSION ::= {
...
}
CNsubgroupID ::= INTEGER (0..7, ...)
CNTypeRestrictionsForEquivalent ::= SEQUENCE (SIZE(1..maxnoofEPLMNs)) OF CNTypeRestrictionsForEquivalentItem
CNTypeRestrictionsForEquivalentItem ::= SEQUENCE {
plmnIdentity PLMNIdentity,
cn-Type ENUMERATED {epc-forbidden, fiveGC-forbidden, ...},
iE-Extensions ProtocolExtensionContainer { {CNTypeRestrictionsForEquivalentItem-ExtIEs} } OPTIONAL,
...
}
CNTypeRestrictionsForEquivalentItem-ExtIEs NGAP-PROTOCOL-EXTENSION ::={
...
}
CNTypeRestrictionsForServing ::= ENUMERATED {
epc-forbidden,
...
}
CommonNetworkInstance ::= OCTET STRING
CompletedCellsInEAI-EUTRA ::= SEQUENCE (SIZE(1..maxnoofCellinEAI)) OF CompletedCellsInEAI-EUTRA-Item
CompletedCellsInEAI-EUTRA-Item ::= SEQUENCE {
eUTRA-CGI EUTRA-CGI,
iE-Extensions ProtocolExtensionContainer { {CompletedCellsInEAI-EUTRA-Item-ExtIEs} } OPTIONAL,
...
}
CompletedCellsInEAI-EUTRA-Item-ExtIEs NGAP-PROTOCOL-EXTENSION ::= {
...
}
CompletedCellsInEAI-NR ::= SEQUENCE (SIZE(1..maxnoofCellinEAI)) OF CompletedCellsInEAI-NR-Item
CompletedCellsInEAI-NR-Item ::= SEQUENCE {
nR-CGI NR-CGI,
iE-Extensions ProtocolExtensionContainer { {CompletedCellsInEAI-NR-Item-ExtIEs} } OPTIONAL,
...
}
CompletedCellsInEAI-NR-Item-ExtIEs NGAP-PROTOCOL-EXTENSION ::= {
...
}
CompletedCellsInTAI-EUTRA ::= SEQUENCE (SIZE(1..maxnoofCellinTAI)) OF CompletedCellsInTAI-EUTRA-Item
CompletedCellsInTAI-EUTRA-Item ::= SEQUENCE{
eUTRA-CGI EUTRA-CGI,
iE-Extensions ProtocolExtensionContainer { {CompletedCellsInTAI-EUTRA-Item-ExtIEs} } OPTIONAL,
...
}
CompletedCellsInTAI-EUTRA-Item-ExtIEs NGAP-PROTOCOL-EXTENSION ::= {
...
}
CompletedCellsInTAI-NR ::= SEQUENCE (SIZE(1..maxnoofCellinTAI)) OF CompletedCellsInTAI-NR-Item
CompletedCellsInTAI-NR-Item ::= SEQUENCE{
nR-CGI NR-CGI,
iE-Extensions ProtocolExtensionContainer { {CompletedCellsInTAI-NR-Item-ExtIEs} } OPTIONAL,
...
}
CompletedCellsInTAI-NR-Item-ExtIEs NGAP-PROTOCOL-EXTENSION ::= {
...
}
ConcurrentWarningMessageInd ::= ENUMERATED {
true,
...
}
ConfidentialityProtectionIndication ::= ENUMERATED {
required,
preferred,
not-needed,
...
}
ConfidentialityProtectionResult ::= ENUMERATED {
performed,
not-performed,
...
}
ConfiguredTACIndication ::= ENUMERATED {
true,
...
}
CoreNetworkAssistanceInformationForInactive ::= SEQUENCE {
uEIdentityIndexValue UEIdentityIndexValue,
uESpecificDRX PagingDRX OPTIONAL,
periodicRegistrationUpdateTimer PeriodicRegistrationUpdateTimer,
mICOModeIndication MICOModeIndication OPTIONAL,
tAIListForInactive TAIListForInactive,
expectedUEBehaviour ExpectedUEBehaviour OPTIONAL,
iE-Extensions ProtocolExtensionContainer { {CoreNetworkAssistanceInformationForInactive-ExtIEs} } OPTIONAL,
...
}
CoreNetworkAssistanceInformationForInactive-ExtIEs NGAP-PROTOCOL-EXTENSION ::= {
{ ID id-EUTRA-PagingeDRXInformation CRITICALITY ignore EXTENSION EUTRA-PagingeDRXInformation PRESENCE optional }|
{ ID id-ExtendedUEIdentityIndexValue CRITICALITY ignore EXTENSION ExtendedUEIdentityIndexValue PRESENCE optional }|
{ ID id-UERadioCapabilityForPaging CRITICALITY ignore EXTENSION UERadioCapabilityForPaging PRESENCE optional }|
{ ID id-MicoAllPLMN CRITICALITY ignore EXTENSION MicoAllPLMN PRESENCE optional }|
{ ID id-NR-PagingeDRXInformation CRITICALITY ignore EXTENSION NR-PagingeDRXInformation PRESENCE optional }|
{ ID id-PagingCauseIndicationForVoiceService CRITICALITY ignore EXTENSION PagingCauseIndicationForVoiceService PRESENCE optional }|
{ ID id-PEIPSassistanceInformation CRITICALITY ignore EXTENSION PEIPSassistanceInformation PRESENCE optional }|
{ ID id-HashedUEIdentityIndexValue CRITICALITY ignore EXTENSION HashedUEIdentityIndexValue PRESENCE optional }|
{ ID id-CN-MT-CommunicationHandling CRITICALITY ignore EXTENSION CN-MT-CommunicationHandling PRESENCE optional },
...
}
CN-MT-CommunicationHandling ::= ENUMERATED {supported, ...}
COUNTValueForPDCP-SN12 ::= SEQUENCE {
pDCP-SN12 INTEGER (0..4095),
hFN-PDCP-SN12 INTEGER (0..1048575),
iE-Extensions ProtocolExtensionContainer { {COUNTValueForPDCP-SN12-ExtIEs} } OPTIONAL,
...
}
COUNTValueForPDCP-SN12-ExtIEs NGAP-PROTOCOL-EXTENSION ::= {
...
}
COUNTValueForPDCP-SN18 ::= SEQUENCE {
pDCP-SN18 INTEGER (0..262143),
hFN-PDCP-SN18 INTEGER (0..16383),
iE-Extensions ProtocolExtensionContainer { {COUNTValueForPDCP-SN18-ExtIEs} } OPTIONAL,
...
}
COUNTValueForPDCP-SN18-ExtIEs NGAP-PROTOCOL-EXTENSION ::= {
...
}
CoverageEnhancementLevel ::= OCTET STRING
CPTransportLayerInformation ::= CHOICE {
endpointIPAddress TransportLayerAddress,
choice-Extensions ProtocolIE-SingleContainer { {CPTransportLayerInformation-ExtIEs} }
}
CPTransportLayerInformation-ExtIEs NGAP-PROTOCOL-IES ::= {
{ ID id-EndpointIPAddressAndPort CRITICALITY reject TYPE EndpointIPAddressAndPort PRESENCE mandatory },
...
}
CriticalityDiagnostics ::= SEQUENCE {
procedureCode ProcedureCode OPTIONAL,
triggeringMessage TriggeringMessage OPTIONAL,
procedureCriticality Criticality OPTIONAL,
iEsCriticalityDiagnostics CriticalityDiagnostics-IE-List OPTIONAL,
iE-Extensions ProtocolExtensionContainer {{CriticalityDiagnostics-ExtIEs}} OPTIONAL,
...
}
CriticalityDiagnostics-ExtIEs NGAP-PROTOCOL-EXTENSION ::= {
...
}
CriticalityDiagnostics-IE-List ::= SEQUENCE (SIZE(1..maxnoofErrors)) OF CriticalityDiagnostics-IE-Item
CriticalityDiagnostics-IE-Item ::= SEQUENCE {
iECriticality Criticality,
iE-ID ProtocolIE-ID,
typeOfError TypeOfError,
iE-Extensions ProtocolExtensionContainer {{CriticalityDiagnostics-IE-Item-ExtIEs}} OPTIONAL,
...
}
CriticalityDiagnostics-IE-Item-ExtIEs NGAP-PROTOCOL-EXTENSION ::= {
...
}
C-RNTI ::= BIT STRING (SIZE(16))
CellBasedMDT-NR::= SEQUENCE {
cellIdListforMDT CellIdListforMDT-NR,
iE-Extensions ProtocolExtensionContainer { {CellBasedMDT-NR-ExtIEs} } OPTIONAL,
...
}
CellBasedMDT-NR-ExtIEs NGAP-PROTOCOL-EXTENSION ::= {
...
}
CellIdListforMDT-NR ::= SEQUENCE (SIZE(1..maxnoofCellIDforMDT)) OF NR-CGI
CellBasedMDT-EUTRA::= SEQUENCE {
cellIdListforMDT CellIdListforMDT-EUTRA,
iE-Extensions ProtocolExtensionContainer { {CellBasedMDT-EUTRA-ExtIEs} } OPTIONAL,
...
}
CellBasedMDT-EUTRA-ExtIEs NGAP-PROTOCOL-EXTENSION ::= {
...
}
CellBasedQMC ::= SEQUENCE {
cellIdListforQMC CellIdListforQMC,
iE-Extensions ProtocolExtensionContainer { {CellBasedQMC-ExtIEs} } OPTIONAL,
...
}
CellBasedQMC-ExtIEs NGAP-PROTOCOL-EXTENSION ::= {
...
}
CellIdListforQMC ::= SEQUENCE (SIZE(1..maxnoofCellIDforQMC)) OF NGRAN-CGI
CellIdListforMDT-EUTRA ::= SEQUENCE (SIZE(1..maxnoofCellIDforMDT)) OF EUTRA-CGI
CAGListforMDT ::= SEQUENCE (SIZE(1.. maxnoofCAGforMDT)) OF CAGListforMDTItem
CAGListforMDTItem ::= SEQUENCE {
plmnID PLMNIdentity,
cAGID CAG-ID,
iE-Extensions ProtocolExtensionContainer { {CAGListforMDTItem-ExtIEs} } OPTIONAL,
...
}
CAGListforMDTItem-ExtIEs NGAP-PROTOCOL-EXTENSION ::={
...
}
-- D
DataCodingScheme ::= BIT STRING (SIZE(8))
DataForwardingAccepted ::= ENUMERATED {
data-forwarding-accepted,
...
}
DataForwardingNotPossible ::= ENUMERATED {
data-forwarding-not-possible,
...
}
DataForwardingResponseDRBList ::= SEQUENCE (SIZE(1..maxnoofDRBs)) OF DataForwardingResponseDRBItem
DataForwardingResponseDRBItem ::= SEQUENCE {
dRB-ID DRB-ID,
dLForwardingUP-TNLInformation UPTransportLayerInformation OPTIONAL,
uLForwardingUP-TNLInformation UPTransportLayerInformation OPTIONAL,
iE-Extensions ProtocolExtensionContainer {{DataForwardingResponseDRBItem-ExtIEs}} OPTIONAL,
...
}
DataForwardingResponseDRBItem-ExtIEs NGAP-PROTOCOL-EXTENSION ::= {
...
}
DAPSRequestInfo ::= SEQUENCE {
dAPSIndicator ENUMERATED {daps-ho-required, ...},
iE-Extensions ProtocolExtensionContainer { {DAPSRequestInfo-ExtIEs} } OPTIONAL,
...
}
DAPSRequestInfo-ExtIEs NGAP-PROTOCOL-EXTENSION ::= {
...
}
DAPSResponseInfoList ::= SEQUENCE (SIZE(1.. maxnoofDRBs)) OF DAPSResponseInfoItem
DAPSResponseInfoItem ::= SEQUENCE {
dRB-ID DRB-ID,
dAPSResponseInfo DAPSResponseInfo,
iE-Extension ProtocolExtensionContainer { {DAPSResponseInfoItem-ExtIEs} } OPTIONAL,
...
}
DAPSResponseInfoItem-ExtIEs NGAP-PROTOCOL-EXTENSION ::= {
...
}
DAPSResponseInfo ::= SEQUENCE {
dapsresponseindicator ENUMERATED {daps-ho-accepted, daps-ho-not-accepted, ...},
iE-Extensions ProtocolExtensionContainer { { DAPSResponseInfo-ExtIEs} } OPTIONAL,
...
}
DAPSResponseInfo-ExtIEs NGAP-PROTOCOL-EXTENSION ::= {
...
}
DataForwardingResponseERABList ::= SEQUENCE (SIZE(1..maxnoofE-RABs)) OF DataForwardingResponseERABListItem
DataForwardingResponseERABListItem ::= SEQUENCE {
e-RAB-ID E-RAB-ID,
dLForwardingUP-TNLInformation UPTransportLayerInformation,
iE-Extensions ProtocolExtensionContainer { {DataForwardingResponseERABListItem-ExtIEs} } OPTIONAL,
...
}
DataForwardingResponseERABListItem-ExtIEs NGAP-PROTOCOL-EXTENSION ::= {
...
}
DelayCritical ::= ENUMERATED {
delay-critical,
non-delay-critical,
...
}
DL-CP-SecurityInformation ::= SEQUENCE {
dl-NAS-MAC DL-NAS-MAC,
iE-Extensions ProtocolExtensionContainer { { DL-CP-SecurityInformation-ExtIEs} } OPTIONAL,
...
}
DL-CP-SecurityInformation-ExtIEs NGAP-PROTOCOL-EXTENSION ::= {
...
}
DL-Signalling ::= ENUMERATED {true, ...}
DL-NAS-MAC ::= BIT STRING (SIZE (16))
DLForwarding ::= ENUMERATED {
dl-forwarding-proposed,
...
}
DL-NGU-TNLInformationReused ::= ENUMERATED {
true,
...
}
DirectForwardingPathAvailability ::= ENUMERATED {
direct-path-available,
...
}
DRB-ID ::= INTEGER (1..32, ...)
DRBsSubjectToStatusTransferList ::= SEQUENCE (SIZE(1..maxnoofDRBs)) OF DRBsSubjectToStatusTransferItem
DRBsSubjectToStatusTransferItem ::= SEQUENCE {
dRB-ID DRB-ID,
dRBStatusUL DRBStatusUL,
dRBStatusDL DRBStatusDL,
iE-Extension ProtocolExtensionContainer { {DRBsSubjectToStatusTransferItem-ExtIEs} } OPTIONAL,
...
}
DRBsSubjectToStatusTransferItem-ExtIEs NGAP-PROTOCOL-EXTENSION ::= {
{ ID id-OldAssociatedQosFlowList-ULendmarkerexpected CRITICALITY ignore EXTENSION AssociatedQosFlowList PRESENCE optional },
...
}
DRBStatusDL ::= CHOICE {
dRBStatusDL12 DRBStatusDL12,
dRBStatusDL18 DRBStatusDL18,
choice-Extensions ProtocolIE-SingleContainer { {DRBStatusDL-ExtIEs} }
}
DRBStatusDL-ExtIEs NGAP-PROTOCOL-IES ::= {
...
}
DRBStatusDL12 ::= SEQUENCE {
dL-COUNTValue COUNTValueForPDCP-SN12,
iE-Extension ProtocolExtensionContainer { {DRBStatusDL12-ExtIEs} } OPTIONAL,
...
}
DRBStatusDL12-ExtIEs NGAP-PROTOCOL-EXTENSION ::= {
...
}
DRBStatusDL18 ::= SEQUENCE {
dL-COUNTValue COUNTValueForPDCP-SN18,
iE-Extension ProtocolExtensionContainer { {DRBStatusDL18-ExtIEs} } OPTIONAL,
...
}
DRBStatusDL18-ExtIEs NGAP-PROTOCOL-EXTENSION ::= {
...
}
DRBStatusUL ::= CHOICE {
dRBStatusUL12 DRBStatusUL12,
dRBStatusUL18 DRBStatusUL18,
choice-Extensions ProtocolIE-SingleContainer { {DRBStatusUL-ExtIEs} }
}
DRBStatusUL-ExtIEs NGAP-PROTOCOL-IES ::= {
...
}
DRBStatusUL12 ::= SEQUENCE {
uL-COUNTValue COUNTValueForPDCP-SN12,
receiveStatusOfUL-PDCP-SDUs BIT STRING (SIZE(1..2048)) OPTIONAL,
iE-Extension ProtocolExtensionContainer { {DRBStatusUL12-ExtIEs} } OPTIONAL,
...
}
DRBStatusUL12-ExtIEs NGAP-PROTOCOL-EXTENSION ::= {
...
}
DRBStatusUL18 ::= SEQUENCE {
uL-COUNTValue COUNTValueForPDCP-SN18,
receiveStatusOfUL-PDCP-SDUs BIT STRING (SIZE(1..131072)) OPTIONAL,
iE-Extension ProtocolExtensionContainer { {DRBStatusUL18-ExtIEs} } OPTIONAL,
...
}
DRBStatusUL18-ExtIEs NGAP-PROTOCOL-EXTENSION ::= {
...
}
DRBsToQosFlowsMappingList ::= SEQUENCE (SIZE(1..maxnoofDRBs)) OF DRBsToQosFlowsMappingItem
DRBsToQosFlowsMappingItem ::= SEQUENCE {
dRB-ID DRB-ID,
associatedQosFlowList AssociatedQosFlowList,
iE-Extensions ProtocolExtensionContainer { {DRBsToQosFlowsMappingItem-ExtIEs} } OPTIONAL,
...
}
DRBsToQosFlowsMappingItem-ExtIEs NGAP-PROTOCOL-EXTENSION ::= {
{ ID id-DAPSRequestInfo CRITICALITY ignore EXTENSION DAPSRequestInfo PRESENCE optional },
...
}
Dynamic5QIDescriptor ::= SEQUENCE {
priorityLevelQos PriorityLevelQos,
packetDelayBudget PacketDelayBudget,
packetErrorRate PacketErrorRate,
fiveQI FiveQI OPTIONAL,
delayCritical DelayCritical OPTIONAL,
-- The above IE shall be present in case of GBR QoS flow
averagingWindow AveragingWindow OPTIONAL,
-- The above IE shall be present in case of GBR QoS flow
maximumDataBurstVolume MaximumDataBurstVolume OPTIONAL,
iE-Extensions ProtocolExtensionContainer { {Dynamic5QIDescriptor-ExtIEs} } OPTIONAL,
...
}
Dynamic5QIDescriptor-ExtIEs NGAP-PROTOCOL-EXTENSION ::= {
{ ID id-ExtendedPacketDelayBudget CRITICALITY ignore EXTENSION ExtendedPacketDelayBudget PRESENCE optional }|
{ ID id-CNPacketDelayBudgetDL CRITICALITY ignore EXTENSION ExtendedPacketDelayBudget PRESENCE optional }|
{ ID id-CNPacketDelayBudgetUL CRITICALITY ignore EXTENSION ExtendedPacketDelayBudget PRESENCE optional },
...
}
-- E
EarlyMeasurement ::= ENUMERATED {true, ...}
EarlyStatusTransfer-TransparentContainer ::= SEQUENCE {
procedureStage ProcedureStageChoice,
iE-Extensions ProtocolExtensionContainer { {EarlyStatusTransfer-TransparentContainer-ExtIEs} } OPTIONAL,
...
}
EarlyStatusTransfer-TransparentContainer-ExtIEs NGAP-PROTOCOL-EXTENSION ::= {
...
}
ProcedureStageChoice ::= CHOICE {
first-dl-count FirstDLCount,
choice-Extensions ProtocolIE-SingleContainer { {ProcedureStageChoice-ExtIEs} }
}
ProcedureStageChoice-ExtIEs NGAP-PROTOCOL-IES ::= {
{ ID id-DLDiscarding CRITICALITY ignore TYPE DLDiscarding PRESENCE mandatory },
...
}
DLDiscarding ::= SEQUENCE {
dRBsSubjectToDLDiscarding DRBsSubjectToDLDiscarding-List,
iE-Extension ProtocolExtensionContainer { {DLDiscarding-ExtIEs} } OPTIONAL,
...
}
DLDiscarding-ExtIEs NGAP-PROTOCOL-EXTENSION ::= {
...
}
DRBsSubjectToDLDiscarding-List ::= SEQUENCE (SIZE (1..maxnoofDRBs)) OF DRBsSubjectToDLDiscarding-Item
DRBsSubjectToDLDiscarding-Item ::= SEQUENCE {
drbID DRB-ID,
dlCount DLCountChoice,
iE-Extension ProtocolExtensionContainer { { DRBsSubjectToDLDiscarding-Item-ExtIEs} } OPTIONAL,
...
}
DRBsSubjectToDLDiscarding-Item-ExtIEs NGAP-PROTOCOL-EXTENSION ::= {
...
}
DLCountChoice ::= CHOICE {
count12bits COUNTValueForPDCP-SN12,
count18bits COUNTValueForPDCP-SN18,
choice-extension ProtocolIE-SingleContainer { {DLCountChoice-ExtIEs} }
}
DLCountChoice-ExtIEs NGAP-PROTOCOL-IES ::= {
...
}
FirstDLCount ::= SEQUENCE {
dRBsSubjectToEarlyStatusTransfer DRBsSubjectToEarlyStatusTransfer-List,
iE-Extension ProtocolExtensionContainer { {FirstDLCount-ExtIEs} } OPTIONAL,
...
}
FirstDLCount-ExtIEs NGAP-PROTOCOL-EXTENSION ::= {
...
}
DRBsSubjectToEarlyStatusTransfer-List ::= SEQUENCE (SIZE (1.. maxnoofDRBs)) OF DRBsSubjectToEarlyStatusTransfer-Item
DRBsSubjectToEarlyStatusTransfer-Item ::= SEQUENCE {
dRB-ID DRB-ID,
firstDLCOUNT DRBStatusDL,
iE-Extension ProtocolExtensionContainer { { DRBsSubjectToEarlyStatusTransfer-Item-ExtIEs} } OPTIONAL,
...
}
DRBsSubjectToEarlyStatusTransfer-Item-ExtIEs NGAP-PROTOCOL-EXTENSION ::= {
...
}
ECNMarkingorCongestionInformationReportingRequest ::= CHOICE {
eCNMarkingAtRANRequest ECNMarkingAtRANRequest,
eCNMarkingAtUPFRequest ECNMarkingAtUPFRequest,
congestionInformationRequest CongestionInformationRequest,
choice-Extensions ProtocolIE-SingleContainer { {ECNMarkingorCongestionInformationReportingRequest-ExtIEs} }
}
ECNMarkingorCongestionInformationReportingRequest-ExtIEs NGAP-PROTOCOL-IES ::= {
...
}
ECNMarkingAtRANRequest ::= ENUMERATED {ul, dl, both, stop, ...}
ECNMarkingAtUPFRequest ::= ENUMERATED {ul, dl, both, stop, ...}
CongestionInformationRequest ::= ENUMERATED {ul, dl, both, stop, ...}
ECNMarkingorCongestionInformationReportingStatus ::= SEQUENCE (SIZE (1..maxnoofQosFlows)) OF ECNMarkingorCongestionInformationReportingStatus-Item
ECNMarkingorCongestionInformationReportingStatus-Item ::= SEQUENCE {
qosFlowIdentifier QosFlowIdentifier,
activationStatus ActivationStatus,
iE-Extension ProtocolExtensionContainer { { ECNMarkingorCongestionInformationReportingStatus-Item-ExtIEs} } OPTIONAL,
...
}
ECNMarkingorCongestionInformationReportingStatus-Item-ExtIEs NGAP-PROTOCOL-EXTENSION ::= {
...
}
ActivationStatus ::= ENUMERATED {
active,
not-active,
...
}
EDT-Session ::= ENUMERATED {
true,
...
}
EmergencyAreaID ::= OCTET STRING (SIZE(3))
EmergencyAreaIDBroadcastEUTRA ::= SEQUENCE (SIZE(1..maxnoofEmergencyAreaID)) OF EmergencyAreaIDBroadcastEUTRA-Item
EmergencyAreaIDBroadcastEUTRA-Item ::= SEQUENCE {
emergencyAreaID EmergencyAreaID,
completedCellsInEAI-EUTRA CompletedCellsInEAI-EUTRA,
iE-Extensions ProtocolExtensionContainer { {EmergencyAreaIDBroadcastEUTRA-Item-ExtIEs} } OPTIONAL,
...
}
EmergencyAreaIDBroadcastEUTRA-Item-ExtIEs NGAP-PROTOCOL-EXTENSION ::= {
...
}
EmergencyAreaIDBroadcastNR ::= SEQUENCE (SIZE(1..maxnoofEmergencyAreaID)) OF EmergencyAreaIDBroadcastNR-Item
EmergencyAreaIDBroadcastNR-Item ::= SEQUENCE {
emergencyAreaID EmergencyAreaID,
completedCellsInEAI-NR CompletedCellsInEAI-NR,
iE-Extensions ProtocolExtensionContainer { {EmergencyAreaIDBroadcastNR-Item-ExtIEs} } OPTIONAL,
...
}
EmergencyAreaIDBroadcastNR-Item-ExtIEs NGAP-PROTOCOL-EXTENSION ::= {
...
}
EmergencyAreaIDCancelledEUTRA ::= SEQUENCE (SIZE(1..maxnoofEmergencyAreaID)) OF EmergencyAreaIDCancelledEUTRA-Item
EmergencyAreaIDCancelledEUTRA-Item ::= SEQUENCE {
emergencyAreaID EmergencyAreaID,
cancelledCellsInEAI-EUTRA CancelledCellsInEAI-EUTRA,
iE-Extensions ProtocolExtensionContainer { {EmergencyAreaIDCancelledEUTRA-Item-ExtIEs} } OPTIONAL,
...
}
EmergencyAreaIDCancelledEUTRA-Item-ExtIEs NGAP-PROTOCOL-EXTENSION ::= {
...
}
EmergencyAreaIDCancelledNR ::= SEQUENCE (SIZE(1..maxnoofEmergencyAreaID)) OF EmergencyAreaIDCancelledNR-Item
EmergencyAreaIDCancelledNR-Item ::= SEQUENCE {
emergencyAreaID EmergencyAreaID,
cancelledCellsInEAI-NR CancelledCellsInEAI-NR,
iE-Extensions ProtocolExtensionContainer { {EmergencyAreaIDCancelledNR-Item-ExtIEs} } OPTIONAL,
...
}
EmergencyAreaIDCancelledNR-Item-ExtIEs NGAP-PROTOCOL-EXTENSION ::= {
...
}
EmergencyAreaIDList ::= SEQUENCE (SIZE(1..maxnoofEmergencyAreaID)) OF EmergencyAreaID
EmergencyAreaIDListForRestart ::= SEQUENCE (SIZE(1..maxnoofEAIforRestart)) OF EmergencyAreaID
EmergencyFallbackIndicator ::= SEQUENCE {
emergencyFallbackRequestIndicator EmergencyFallbackRequestIndicator,
emergencyServiceTargetCN EmergencyServiceTargetCN OPTIONAL,
iE-Extensions ProtocolExtensionContainer { {EmergencyFallbackIndicator-ExtIEs} } OPTIONAL,
...
}
EmergencyFallbackIndicator-ExtIEs NGAP-PROTOCOL-EXTENSION ::= {
...
}
EmergencyFallbackRequestIndicator ::= ENUMERATED {
emergency-fallback-requested,
...
}
EmergencyServiceTargetCN ::= ENUMERATED {
fiveGC,
epc,
...
}
ENB-ID ::= CHOICE {
macroENB-ID BIT STRING (SIZE(20)),
homeENB-ID BIT STRING (SIZE(28)),
short-macroENB-ID BIT STRING (SIZE(18)),
long-macroENB-ID BIT STRING (SIZE(21)),
choice-Extensions ProtocolIE-SingleContainer { { ENB-ID-ExtIEs} }
}
ENB-ID-ExtIEs NGAP-PROTOCOL-IES ::= {
...
}
Enhanced-CoverageRestriction ::= ENUMERATED {restricted, ... }
Extended-ConnectedTime ::= INTEGER (0..255)
EN-DCSONConfigurationTransfer ::= OCTET STRING
EndpointIPAddressAndPort ::=SEQUENCE {
endpointIPAddress TransportLayerAddress,
portNumber PortNumber,
iE-Extensions ProtocolExtensionContainer { { EndpointIPAddressAndPort-ExtIEs} } OPTIONAL
}
EndIndication ::= ENUMERATED {
no-further-data,
further-data-exists,
...
}
EndpointIPAddressAndPort-ExtIEs NGAP-PROTOCOL-EXTENSION ::= {
...
}
EquivalentPLMNs ::= SEQUENCE (SIZE(1..maxnoofEPLMNs)) OF PLMNIdentity
EPS-TAC ::= OCTET STRING (SIZE(2))
EPS-TAI ::= SEQUENCE {
pLMNIdentity PLMNIdentity,
ePS-TAC EPS-TAC,
iE-Extensions ProtocolExtensionContainer { {EPS-TAI-ExtIEs} } OPTIONAL,
...
}
EPS-TAI-ExtIEs NGAP-PROTOCOL-EXTENSION ::= {
...
}
E-RAB-ID ::= INTEGER (0..15, ...)
E-RABInformationList ::= SEQUENCE (SIZE(1..maxnoofE-RABs)) OF E-RABInformationItem
E-RABInformationItem ::= SEQUENCE {
e-RAB-ID E-RAB-ID,
dLForwarding DLForwarding OPTIONAL,
iE-Extensions ProtocolExtensionContainer { {E-RABInformationItem-ExtIEs} } OPTIONAL,
...
}
E-RABInformationItem-ExtIEs NGAP-PROTOCOL-EXTENSION ::= {
{ID id-SourceTNLAddrInfo CRITICALITY ignore EXTENSION TransportLayerAddress PRESENCE optional}|
{ID id-SourceNodeTNLAddrInfo CRITICALITY ignore EXTENSION TransportLayerAddress PRESENCE optional},
...
}
ERedCapIndication ::= ENUMERATED {
true,
...
}
EUTRACellIdentity ::= BIT STRING (SIZE(28))
EUTRA-CGI ::= SEQUENCE {
pLMNIdentity PLMNIdentity,
eUTRACellIdentity EUTRACellIdentity,
iE-Extensions ProtocolExtensionContainer { {EUTRA-CGI-ExtIEs} } OPTIONAL,
...
}
EUTRA-CGI-ExtIEs NGAP-PROTOCOL-EXTENSION ::= {
...
}
EUTRA-CGIList ::= SEQUENCE (SIZE(1..maxnoofCellsinngeNB)) OF EUTRA-CGI
EUTRA-CGIListForWarning ::= SEQUENCE (SIZE(1..maxnoofCellIDforWarning)) OF EUTRA-CGI
EUTRA-PagingeDRXInformation ::= SEQUENCE {
eUTRA-paging-eDRX-Cycle EUTRA-Paging-eDRX-Cycle,
eUTRA-paging-Time-Window EUTRA-Paging-Time-Window OPTIONAL,
iE-Extensions ProtocolExtensionContainer { {EUTRA-PagingeDRXInformation-ExtIEs} } OPTIONAL,
...
}
EUTRA-PagingeDRXInformation-ExtIEs NGAP-PROTOCOL-EXTENSION ::= {
...
}
EUTRA-Paging-eDRX-Cycle ::= ENUMERATED {
hfhalf, hf1, hf2, hf4, hf6,
hf8, hf10, hf12, hf14, hf16,
hf32, hf64, hf128, hf256,
...
}
EUTRA-Paging-Time-Window ::= ENUMERATED {
s1, s2, s3, s4, s5,
s6, s7, s8, s9, s10,
s11, s12, s13, s14, s15, s16,
...
}
EUTRAencryptionAlgorithms ::= BIT STRING (SIZE(16, ...))
EUTRAintegrityProtectionAlgorithms ::= BIT STRING (SIZE(16, ...))
EventType ::= ENUMERATED {
direct,
change-of-serve-cell,
ue-presence-in-area-of-interest,
stop-change-of-serve-cell,
stop-ue-presence-in-area-of-interest,
cancel-location-reporting-for-the-ue,
...,
change-of-serving-cell-and-UE-presence-in-the-Area-of-Interest
}
ExcessPacketDelayThresholdConfiguration ::= SEQUENCE (SIZE(1..maxnoofThresholdsForExcessPacketDelay)) OF ExcessPacketDelayThresholdItem
ExcessPacketDelayThresholdItem ::= SEQUENCE {
fiveQi FiveQI,
excessPacketDelayThresholdValue ExcessPacketDelayThresholdValue,
iE-Extensions ProtocolExtensionContainer { { ExcessPacketDelayThresholdItem-ExtIEs} } OPTIONAL,
...
}
ExcessPacketDelayThresholdItem-ExtIEs NGAP-PROTOCOL-EXTENSION ::= {
...
}
ExcessPacketDelayThresholdValue ::= ENUMERATED {
ms0dot25, ms0dot5, ms1, ms2, ms4, ms5, ms10, ms20, ms30, ms40, ms50, ms60, ms70, ms80, ms90, ms100, ms150, ms300, ms500,
...
}
ExpectedActivityPeriod ::= INTEGER (1..30|40|50|60|80|100|120|150|180|181, ...)
ExpectedHOInterval ::= ENUMERATED {
sec15, sec30, sec60, sec90, sec120, sec180, long-time,
...
}
ExpectedIdlePeriod ::= INTEGER (1..30|40|50|60|80|100|120|150|180|181, ...)
ExpectedUEActivityBehaviour ::= SEQUENCE {
expectedActivityPeriod ExpectedActivityPeriod OPTIONAL,
expectedIdlePeriod ExpectedIdlePeriod OPTIONAL,
sourceOfUEActivityBehaviourInformation SourceOfUEActivityBehaviourInformation OPTIONAL,
iE-Extensions ProtocolExtensionContainer { {ExpectedUEActivityBehaviour-ExtIEs} } OPTIONAL,
...
}
ExpectedUEActivityBehaviour-ExtIEs NGAP-PROTOCOL-EXTENSION ::= {
...
}
ExpectedUEBehaviour ::= SEQUENCE {
expectedUEActivityBehaviour ExpectedUEActivityBehaviour OPTIONAL,
expectedHOInterval ExpectedHOInterval OPTIONAL,
expectedUEMobility ExpectedUEMobility OPTIONAL,
expectedUEMovingTrajectory ExpectedUEMovingTrajectory OPTIONAL,
iE-Extensions ProtocolExtensionContainer { {ExpectedUEBehaviour-ExtIEs} } OPTIONAL,
...
}
ExpectedUEBehaviour-ExtIEs NGAP-PROTOCOL-EXTENSION ::= {
...
}
ExpectedUEMobility ::= ENUMERATED {
stationary,
mobile,
...
}
ExpectedUEMovingTrajectory ::= SEQUENCE (SIZE(1..maxnoofCellsUEMovingTrajectory)) OF ExpectedUEMovingTrajectoryItem
ExpectedUEMovingTrajectoryItem ::= SEQUENCE {
nGRAN-CGI NGRAN-CGI,
timeStayedInCell INTEGER (0..4095) OPTIONAL,
iE-Extensions ProtocolExtensionContainer { {ExpectedUEMovingTrajectoryItem-ExtIEs} } OPTIONAL,
...
}
ExpectedUEMovingTrajectoryItem-ExtIEs NGAP-PROTOCOL-EXTENSION ::= {
...
}
Extended-AMFName ::= SEQUENCE {
aMFNameVisibleString AMFNameVisibleString OPTIONAL,
aMFNameUTF8String AMFNameUTF8String OPTIONAL,
iE-Extensions ProtocolExtensionContainer { { Extended-AMFName-ExtIEs } } OPTIONAL,
...
}
Extended-AMFName-ExtIEs NGAP-PROTOCOL-EXTENSION ::= {
...
}
ExtendedPacketDelayBudget ::= INTEGER (1..65535, ..., 65536..109999)
Extended-RANNodeName ::= SEQUENCE {
rANNodeNameVisibleString RANNodeNameVisibleString OPTIONAL,
rANNodeNameUTF8String RANNodeNameUTF8String OPTIONAL,
iE-Extensions ProtocolExtensionContainer { { Extended-RANNodeName-ExtIEs } } OPTIONAL,
...
}
Extended-RANNodeName-ExtIEs NGAP-PROTOCOL-EXTENSION ::= {
...
}
ExtendedRATRestrictionInformation ::= SEQUENCE {
primaryRATRestriction BIT STRING (SIZE(8, ..., 16)),
secondaryRATRestriction BIT STRING (SIZE(8, ...)),
iE-Extensions ProtocolExtensionContainer { {ExtendedRATRestrictionInformation-ExtIEs} } OPTIONAL,
...
}
ExtendedRATRestrictionInformation-ExtIEs NGAP-PROTOCOL-EXTENSION ::= {
...
}
ExtendedRNC-ID ::= INTEGER (4096..65535)
ExtendedSliceSupportList ::= SEQUENCE (SIZE(1..maxnoofExtSliceItems)) OF SliceSupportItem
ExtendedUEIdentityIndexValue ::= BIT STRING (SIZE(16))
EventTrigger::= CHOICE {
outOfCoverage ENUMERATED {true, ...},
eventL1LoggedMDTConfig EventL1LoggedMDTConfig,
choice-Extensions ProtocolIE-SingleContainer { { EventTrigger-ExtIEs} }
}
EventTrigger-ExtIEs NGAP-PROTOCOL-IES ::= {
...
}
EventL1LoggedMDTConfig ::= SEQUENCE {
l1Threshold MeasurementThresholdL1LoggedMDT,
hysteresis Hysteresis,
timeToTrigger TimeToTrigger,
iE-Extensions ProtocolExtensionContainer { { EventL1LoggedMDTConfig-ExtIEs} } OPTIONAL,
...
}
EventL1LoggedMDTConfig-ExtIEs NGAP-PROTOCOL-EXTENSION ::= {
...
}
MeasurementThresholdL1LoggedMDT ::= CHOICE {
threshold-RSRP Threshold-RSRP,
threshold-RSRQ Threshold-RSRQ,
choice-Extensions ProtocolIE-SingleContainer { { MeasurementThresholdL1LoggedMDT-ExtIEs} }
}
MeasurementThresholdL1LoggedMDT-ExtIEs NGAP-PROTOCOL-IES ::= {
...
}
EquivalentSNPNsList ::= SEQUENCE (SIZE(1..maxnoofESNPNs)) OF EquivalentSNPNsItem
EquivalentSNPNsItem ::= SEQUENCE {
plmnIdentity PLMNIdentity,
nID NID,
iE-Extensions ProtocolExtensionContainer { {EquivalentSNPNsItem-ExtIEs} } OPTIONAL,
...
}
EquivalentSNPNsItem-ExtIEs NGAP-PROTOCOL-EXTENSION ::={
...
}
-- F
FailureIndication ::= SEQUENCE {
uERLFReportContainer UERLFReportContainer,
iE-Extensions ProtocolExtensionContainer { { FailureIndication-ExtIEs} } OPTIONAL,
...
}
FailureIndication-ExtIEs NGAP-PROTOCOL-EXTENSION ::= {
...
}
FiveGCAction ::= CHOICE {
hLComActivate HLComActivate,
hLComDeactivate HLComDeactivate,
choice-Extensions ProtocolIE-SingleContainer { {FiveGCAction-ExtIEs} }
}
FiveGCAction-ExtIEs NGAP-PROTOCOL-IES ::= {
...
}
FiveG-ProSeAuthorized ::= SEQUENCE {
fiveGProSeDirectDiscovery FiveGProSeDirectDiscovery OPTIONAL,
fiveGProSeDirectCommunication FiveGProSeDirectCommunication OPTIONAL,
fiveGProSeLayer2UEtoNetworkRelay FiveGProSeLayer2UEtoNetworkRelay OPTIONAL,
fiveGProSeLayer3UEtoNetworkRelay FiveGProSeLayer3UEtoNetworkRelay OPTIONAL,
fiveGProSeLayer2RemoteUE FiveGProSeLayer2RemoteUE OPTIONAL,
iE-Extensions ProtocolExtensionContainer { {FiveG-ProSeAuthorized-ExtIEs} } OPTIONAL,
...
}
FiveG-ProSeAuthorized-ExtIEs NGAP-PROTOCOL-EXTENSION ::= {
{ ID id-FiveGProSeLayer2Multipath CRITICALITY ignore EXTENSION FiveGProSeLayer2Multipath PRESENCE optional }|
{ ID id-FiveGProSeLayer2UEtoUERelay CRITICALITY ignore EXTENSION FiveGProSeLayer2UEtoUERelay PRESENCE optional }|
{ ID id-FiveGProSeLayer2UEtoUERemote CRITICALITY ignore EXTENSION FiveGProSeLayer2UEtoUERemote PRESENCE optional },
...
}
FiveGProSeDirectDiscovery ::= ENUMERATED {
authorized,
not-authorized,
...
}
FiveGProSeDirectCommunication ::= ENUMERATED {
authorized,
not-authorized,
...
}
FiveGProSeLayer2UEtoNetworkRelay ::= ENUMERATED {
authorized,
not-authorized,
...
}
FiveGProSeLayer3UEtoNetworkRelay ::= ENUMERATED {
authorized,
not-authorized,
...
}
FiveGProSeLayer2RemoteUE ::= ENUMERATED {
authorized,
not-authorized,
...
}
FiveGProSeLayer2Multipath ::= ENUMERATED {
authorized,
not-authorized,
...
}
FiveGProSeLayer2UEtoUERelay ::= ENUMERATED {
authorized,
not-authorized,
...
}
FiveGProSeLayer2UEtoUERemote ::= ENUMERATED {
authorized,
not-authorized,
...
}
FiveG-ProSePC5QoSParameters ::= SEQUENCE {
fiveGProSepc5QoSFlowList FiveGProSePC5QoSFlowList,
fiveGProSepc5LinkAggregateBitRates BitRate OPTIONAL,
iE-Extensions ProtocolExtensionContainer { { FiveG-ProSePC5QoSParameters-ExtIEs} } OPTIONAL,
...
}
FiveG-ProSePC5QoSParameters-ExtIEs NGAP-PROTOCOL-EXTENSION ::= {
...
}
FiveGProSePC5QoSFlowList ::= SEQUENCE (SIZE(1..maxnoofPC5QoSFlows)) OF FiveGProSePC5QoSFlowItem
FiveGProSePC5QoSFlowItem ::= SEQUENCE {
fiveGproSepQI FiveQI,
fiveGproSepc5FlowBitRates FiveGProSePC5FlowBitRates OPTIONAL,
fiveGproSerange Range OPTIONAL,
iE-Extensions ProtocolExtensionContainer { { FiveGProSePC5QoSFlowItem-ExtIEs} } OPTIONAL,
...
}
FiveGProSePC5QoSFlowItem-ExtIEs NGAP-PROTOCOL-EXTENSION ::= {
...
}
FiveGProSePC5FlowBitRates ::= SEQUENCE {
fiveGproSeguaranteedFlowBitRate BitRate,
fiveGproSemaximumFlowBitRate BitRate,
iE-Extensions ProtocolExtensionContainer { { FiveGProSePC5FlowBitRates-ExtIEs} } OPTIONAL,
...
}
FiveGProSePC5FlowBitRates-ExtIEs NGAP-PROTOCOL-EXTENSION ::= {
...
}
FiveG-S-TMSI ::= SEQUENCE {
aMFSetID AMFSetID,
aMFPointer AMFPointer,
fiveG-TMSI FiveG-TMSI,
iE-Extensions ProtocolExtensionContainer { {FiveG-S-TMSI-ExtIEs} } OPTIONAL,
...
}
FiveG-S-TMSI-ExtIEs NGAP-PROTOCOL-EXTENSION ::= {
...
}
FiveG-TMSI ::= OCTET STRING (SIZE(4))
FiveQI ::= INTEGER (0..255, ...)
ForbiddenAreaInformation ::= SEQUENCE (SIZE(1.. maxnoofEPLMNsPlusOne)) OF ForbiddenAreaInformation-Item
ForbiddenAreaInformation-Item ::= SEQUENCE {
pLMNIdentity PLMNIdentity,
forbiddenTACs ForbiddenTACs,
iE-Extensions ProtocolExtensionContainer { {ForbiddenAreaInformation-Item-ExtIEs} } OPTIONAL,
...
}
ForbiddenAreaInformation-Item-ExtIEs NGAP-PROTOCOL-EXTENSION ::= {
...
}
ForbiddenTACs ::= SEQUENCE (SIZE(1..maxnoofForbTACs)) OF TAC
FromEUTRANtoNGRAN ::= SEQUENCE {
sourceeNBID IntersystemSONeNBID,
targetNGRANnodeID IntersystemSONNGRANnodeID,
iE-Extensions ProtocolExtensionContainer { { FromEUTRANtoNGRAN-ExtIEs} } OPTIONAL
}
FromEUTRANtoNGRAN-ExtIEs NGAP-PROTOCOL-EXTENSION ::= {
...
}
FromNGRANtoEUTRAN ::= SEQUENCE {
sourceNGRANnodeID IntersystemSONNGRANnodeID,
targeteNBID IntersystemSONeNBID,
iE-Extensions ProtocolExtensionContainer { { FromNGRANtoEUTRAN-ExtIEs} } OPTIONAL
}
FromNGRANtoEUTRAN-ExtIEs NGAP-PROTOCOL-EXTENSION ::= {
...
}
-- G
GBR-QosInformation ::= SEQUENCE {
maximumFlowBitRateDL BitRate,
maximumFlowBitRateUL BitRate,
guaranteedFlowBitRateDL BitRate,
guaranteedFlowBitRateUL BitRate,
notificationControl NotificationControl OPTIONAL,
maximumPacketLossRateDL PacketLossRate OPTIONAL,
maximumPacketLossRateUL PacketLossRate OPTIONAL,
iE-Extensions ProtocolExtensionContainer { {GBR-QosInformation-ExtIEs} } OPTIONAL,
...
}
GBR-QosInformation-ExtIEs NGAP-PROTOCOL-EXTENSION ::= {
{ ID id-AlternativeQoSParaSetList CRITICALITY ignore EXTENSION AlternativeQoSParaSetList PRESENCE optional },
...
}
GlobalCable-ID ::= OCTET STRING
GlobalCable-ID-new ::= SEQUENCE {
globalCable-ID GlobalCable-ID,
tAI TAI,
iE-Extensions ProtocolExtensionContainer { { GlobalCable-ID-new-ExtIEs} } OPTIONAL,
...
}
GlobalCable-ID-new-ExtIEs NGAP-PROTOCOL-EXTENSION ::= {
...
}
GlobalENB-ID ::= SEQUENCE {
pLMNidentity PLMNIdentity,
eNB-ID ENB-ID,
iE-Extensions ProtocolExtensionContainer { {GlobalENB-ID-ExtIEs} } OPTIONAL,
...
}
GlobalENB-ID-ExtIEs NGAP-PROTOCOL-EXTENSION ::= {
...
}
GlobalGNB-ID ::= SEQUENCE {
pLMNIdentity PLMNIdentity,
gNB-ID GNB-ID,
iE-Extensions ProtocolExtensionContainer { {GlobalGNB-ID-ExtIEs} } OPTIONAL,
...
}
GlobalGNB-ID-ExtIEs NGAP-PROTOCOL-EXTENSION ::= {
...
}
GlobalN3IWF-ID ::= SEQUENCE {
pLMNIdentity PLMNIdentity,
n3IWF-ID N3IWF-ID,
iE-Extensions ProtocolExtensionContainer { {GlobalN3IWF-ID-ExtIEs} } OPTIONAL,
...
}
GlobalN3IWF-ID-ExtIEs NGAP-PROTOCOL-EXTENSION ::= {
...
}
GlobalLine-ID ::= SEQUENCE {
globalLineIdentity GlobalLineIdentity,
lineType LineType OPTIONAL,
iE-Extensions ProtocolExtensionContainer { {GlobalLine-ID-ExtIEs} } OPTIONAL,
...
}
GlobalLine-ID-ExtIEs NGAP-PROTOCOL-EXTENSION ::= {
{ ID id-TAI CRITICALITY ignore EXTENSION TAI PRESENCE optional },
...
}
GlobalLineIdentity ::= OCTET STRING
GlobalNgENB-ID ::= SEQUENCE {
pLMNIdentity PLMNIdentity,
ngENB-ID NgENB-ID,
iE-Extensions ProtocolExtensionContainer { {GlobalNgENB-ID-ExtIEs} } OPTIONAL,
...
}
GlobalNgENB-ID-ExtIEs NGAP-PROTOCOL-EXTENSION ::= {
...
}
GlobalRANNodeID ::= CHOICE {
globalGNB-ID GlobalGNB-ID,
globalNgENB-ID GlobalNgENB-ID,
globalN3IWF-ID GlobalN3IWF-ID,
choice-Extensions ProtocolIE-SingleContainer { {GlobalRANNodeID-ExtIEs} }
}
GlobalRANNodeID-ExtIEs NGAP-PROTOCOL-IES ::= {
{ ID id-GlobalTNGF-ID CRITICALITY reject TYPE GlobalTNGF-ID PRESENCE mandatory }|
{ ID id-GlobalTWIF-ID CRITICALITY reject TYPE GlobalTWIF-ID PRESENCE mandatory }|
{ ID id-GlobalW-AGF-ID CRITICALITY reject TYPE GlobalW-AGF-ID PRESENCE mandatory },
...
}
GlobalTNGF-ID ::= SEQUENCE {
pLMNIdentity PLMNIdentity,
tNGF-ID TNGF-ID,
iE-Extensions ProtocolExtensionContainer { { GlobalTNGF-ID-ExtIEs} } OPTIONAL,
...
}
GlobalTNGF-ID-ExtIEs NGAP-PROTOCOL-EXTENSION ::= {
...
}
GlobalTWIF-ID ::= SEQUENCE {
pLMNIdentity PLMNIdentity,
tWIF-ID TWIF-ID,
iE-Extensions ProtocolExtensionContainer { { GlobalTWIF-ID-ExtIEs} } OPTIONAL,
...
}
GlobalTWIF-ID-ExtIEs NGAP-PROTOCOL-EXTENSION ::= {
...
}
GlobalW-AGF-ID ::= SEQUENCE {
pLMNIdentity PLMNIdentity,
w-AGF-ID W-AGF-ID,
iE-Extensions ProtocolExtensionContainer { { GlobalW-AGF-ID-ExtIEs} } OPTIONAL,
...
}
GlobalW-AGF-ID-ExtIEs NGAP-PROTOCOL-EXTENSION ::= {
...
}
GNB-ID ::= CHOICE {
gNB-ID BIT STRING (SIZE(22..32)),
choice-Extensions ProtocolIE-SingleContainer { {GNB-ID-ExtIEs} }
}
GNB-ID-ExtIEs NGAP-PROTOCOL-IES ::= {
...
}
GTP-TEID ::= OCTET STRING (SIZE(4))
GTPTunnel ::= SEQUENCE {
transportLayerAddress TransportLayerAddress,
gTP-TEID GTP-TEID,
iE-Extensions ProtocolExtensionContainer { {GTPTunnel-ExtIEs} } OPTIONAL,
...
}
GTPTunnel-ExtIEs NGAP-PROTOCOL-EXTENSION ::= {
...
}
GUAMI ::= SEQUENCE {
pLMNIdentity PLMNIdentity,
aMFRegionID AMFRegionID,
aMFSetID AMFSetID,
aMFPointer AMFPointer,
iE-Extensions ProtocolExtensionContainer { {GUAMI-ExtIEs} } OPTIONAL,
...
}
GUAMI-ExtIEs NGAP-PROTOCOL-EXTENSION ::= {
...
}
GUAMIType ::= ENUMERATED {native, mapped, ...}
-- H
HandoverCommandTransfer ::= SEQUENCE {
dLForwardingUP-TNLInformation UPTransportLayerInformation OPTIONAL,
qosFlowToBeForwardedList QosFlowToBeForwardedList OPTIONAL,
dataForwardingResponseDRBList DataForwardingResponseDRBList OPTIONAL,
iE-Extensions ProtocolExtensionContainer { {HandoverCommandTransfer-ExtIEs} } OPTIONAL,
...
}
HandoverCommandTransfer-ExtIEs NGAP-PROTOCOL-EXTENSION ::= {
{ ID id-AdditionalDLForwardingUPTNLInformation CRITICALITY ignore EXTENSION QosFlowPerTNLInformationList PRESENCE optional }|
{ ID id-ULForwardingUP-TNLInformation CRITICALITY reject EXTENSION UPTransportLayerInformation PRESENCE optional }|
{ ID id-AdditionalULForwardingUPTNLInformation CRITICALITY reject EXTENSION UPTransportLayerInformationList PRESENCE optional }|
{ ID id-DataForwardingResponseERABList CRITICALITY ignore EXTENSION DataForwardingResponseERABList PRESENCE optional }|
{ ID id-QosFlowFailedToSetupList CRITICALITY ignore EXTENSION QosFlowListWithCause PRESENCE optional },
...
}
HandoverFlag ::= ENUMERATED {
handover-preparation,
...
}
HandoverPreparationUnsuccessfulTransfer ::= SEQUENCE {
cause Cause,
iE-Extensions ProtocolExtensionContainer { {HandoverPreparationUnsuccessfulTransfer-ExtIEs} } OPTIONAL,
...
}
HandoverPreparationUnsuccessfulTransfer-ExtIEs NGAP-PROTOCOL-EXTENSION ::= {
...
}
HandoverRequestAcknowledgeTransfer ::= SEQUENCE {
dL-NGU-UP-TNLInformation UPTransportLayerInformation,
dLForwardingUP-TNLInformation UPTransportLayerInformation OPTIONAL,
securityResult SecurityResult OPTIONAL,
qosFlowSetupResponseList QosFlowListWithDataForwarding,
qosFlowFailedToSetupList QosFlowListWithCause OPTIONAL,
dataForwardingResponseDRBList DataForwardingResponseDRBList OPTIONAL,
iE-Extensions ProtocolExtensionContainer { {HandoverRequestAcknowledgeTransfer-ExtIEs} } OPTIONAL,
...
}
HandoverRequestAcknowledgeTransfer-ExtIEs NGAP-PROTOCOL-EXTENSION ::= {
{ ID id-AdditionalDLUPTNLInformationForHOList CRITICALITY ignore EXTENSION AdditionalDLUPTNLInformationForHOList PRESENCE optional }|
{ ID id-ULForwardingUP-TNLInformation CRITICALITY reject EXTENSION UPTransportLayerInformation PRESENCE optional }|
{ ID id-AdditionalULForwardingUPTNLInformation CRITICALITY reject EXTENSION UPTransportLayerInformationList PRESENCE optional }|
{ ID id-DataForwardingResponseERABList CRITICALITY ignore EXTENSION DataForwardingResponseERABList PRESENCE optional }|
{ ID id-RedundantDL-NGU-UP-TNLInformation CRITICALITY ignore EXTENSION UPTransportLayerInformation PRESENCE optional }|
{ ID id-UsedRSNInformation CRITICALITY ignore EXTENSION RedundantPDUSessionInformation PRESENCE optional }|
{ ID id-GlobalRANNodeID CRITICALITY ignore EXTENSION GlobalRANNodeID PRESENCE optional }|
{ ID id-MBS-SupportIndicator CRITICALITY ignore EXTENSION MBS-SupportIndicator PRESENCE optional }|
{ ID id-PDUSetbasedHandlingIndicator CRITICALITY ignore EXTENSION PDUSetbasedHandlingIndicator PRESENCE optional }|
{ ID id-ECNMarkingorCongestionInformationReportingStatus CRITICALITY ignore EXTENSION ECNMarkingorCongestionInformationReportingStatus PRESENCE optional },
...
}
HandoverRequiredTransfer ::= SEQUENCE {
directForwardingPathAvailability DirectForwardingPathAvailability OPTIONAL,
iE-Extensions ProtocolExtensionContainer { {HandoverRequiredTransfer-ExtIEs} } OPTIONAL,
...
}
HandoverRequiredTransfer-ExtIEs NGAP-PROTOCOL-EXTENSION ::= {
...
}
HandoverResourceAllocationUnsuccessfulTransfer ::= SEQUENCE {
cause Cause,
criticalityDiagnostics CriticalityDiagnostics OPTIONAL,
iE-Extensions ProtocolExtensionContainer { {HandoverResourceAllocationUnsuccessfulTransfer-ExtIEs} } OPTIONAL,
...
}
HandoverResourceAllocationUnsuccessfulTransfer-ExtIEs NGAP-PROTOCOL-EXTENSION ::= {
...
}
HandoverType ::= ENUMERATED {
intra5gs,
fivegs-to-eps,
eps-to-5gs,
...,
fivegs-to-utran
}
HashedUEIdentityIndexValue ::= BIT STRING (SIZE(13, ...))
HFCNode-ID ::= OCTET STRING
HFCNode-ID-new ::= SEQUENCE {
hFCNode-ID HFCNode-ID,
tAI TAI,
iE-Extensions ProtocolExtensionContainer { { HFCNode-ID-new-ExtIEs} } OPTIONAL,
...
}
HFCNode-ID-new-ExtIEs NGAP-PROTOCOL-EXTENSION ::= {
{ ID id-GlobalCable-ID CRITICALITY ignore EXTENSION GlobalCable-ID PRESENCE optional },
...
}
HLComActivate ::= SEQUENCE {
nR-Paging-Long-eDRX-Information-for-RRC-INACTIVE NR-Paging-Long-eDRX-Information-for-RRC-INACTIVE,
iE-Extensions ProtocolExtensionContainer { { HLComActivate-ExtIEs} } OPTIONAL,
...
}
HLComActivate-ExtIEs NGAP-PROTOCOL-EXTENSION ::= {
...
}
HLComDeactivate ::= SEQUENCE {
uEReachabilityIndication ENUMERATED {true, ...},
iE-Extensions ProtocolExtensionContainer { { HLComDeactivate-ExtIEs} } OPTIONAL,
...
}
HLComDeactivate-ExtIEs NGAP-PROTOCOL-EXTENSION ::= {
...
}
HOReport::= SEQUENCE {
handoverReportType ENUMERATED {ho-too-early, ho-to-wrong-cell, intersystem-ping-pong, ...},
handoverCause Cause,
sourcecellCGI NGRAN-CGI,
targetcellCGI NGRAN-CGI,
reestablishmentcellCGI NGRAN-CGI OPTIONAL,
-- The above IE shall be present if the Handover Report Type IE is set to the value "HO to wrong cell"
sourcecellC-RNTI BIT STRING (SIZE(16)) OPTIONAL,
targetcellinE-UTRAN EUTRA-CGI OPTIONAL,
-- The above IE shall be present if the Handover Report Type IE is set to the value "Inter System ping-pong"
mobilityInformation MobilityInformation OPTIONAL,
uERLFReportContainer UERLFReportContainer OPTIONAL,
iE-Extensions ProtocolExtensionContainer { { HOReport-ExtIEs} } OPTIONAL,
...
}
HOReport-ExtIEs NGAP-PROTOCOL-EXTENSION ::= {
{ ID id-ExtendedMobilityInformation CRITICALITY ignore EXTENSION ExtendedMobilityInformation PRESENCE optional }|
{ ID id-TargetCellCRNTI CRITICALITY ignore EXTENSION C-RNTI PRESENCE optional }|
{ ID id-TimeSinceFailure CRITICALITY ignore EXTENSION TimeSinceFailure PRESENCE optional },
...
}
Hysteresis ::= INTEGER (0..30)
-- I
IAB-Authorized ::= ENUMERATED {
authorized,
not-authorized,
...
}
MobileIAB-MTUserLocationInformation ::= SEQUENCE {
nRCGI NR-CGI,
tAI TAI,
iE-Extensions ProtocolExtensionContainer { { MobileIAB-MTUserLocationInformation-ExtIEs} } OPTIONAL,
...
}
MobileIAB-MTUserLocationInformation-ExtIEs NGAP-PROTOCOL-EXTENSION ::= {
...
}
IAB-Supported ::= ENUMERATED {
true,
...
}
IABNodeIndication ::= ENUMERATED {
true,
...
}
IMSVoiceSupportIndicator ::= ENUMERATED {
supported,
not-supported,
...
}
IndexToRFSP ::= INTEGER (1..256, ...)
InfoOnRecommendedCellsAndRANNodesForPaging ::= SEQUENCE {
recommendedCellsForPaging RecommendedCellsForPaging,
recommendRANNodesForPaging RecommendedRANNodesForPaging,
iE-Extensions ProtocolExtensionContainer { {InfoOnRecommendedCellsAndRANNodesForPaging-ExtIEs} } OPTIONAL,
...
}
InfoOnRecommendedCellsAndRANNodesForPaging-ExtIEs NGAP-PROTOCOL-EXTENSION ::= {
...
}
IntegrityProtectionIndication ::= ENUMERATED {
required,
preferred,
not-needed,
...
}
IntegrityProtectionResult ::= ENUMERATED {
performed,
not-performed,
...
}
IntendedNumberOfPagingAttempts ::= INTEGER (1..16, ...)
InterfacesToTrace ::= BIT STRING (SIZE(8))
ImmediateMDTNr ::= SEQUENCE {
measurementsToActivate MeasurementsToActivate,
m1Configuration M1Configuration OPTIONAL,
-- The above IE shall be present if the Measurements to Activate IE has the first bit set to "1"
m4Configuration M4Configuration OPTIONAL,
-- The above IE shall be present if the Measurements to Activate IE has the third bit set to "1"
m5Configuration M5Configuration OPTIONAL,
-- The above IE shall be present if the Measurements to Activate IE has the fourth bit set to "1"
m6Configuration M6Configuration OPTIONAL,
-- The above IE shall be present if the Measurements to Activate IE has the fifth bit set to "1"
m7Configuration M7Configuration OPTIONAL,
-- The above IE shall be present if the Measurements to Activate IE has the sixth bit set to "1"
bluetoothMeasurementConfiguration BluetoothMeasurementConfiguration OPTIONAL,
wLANMeasurementConfiguration WLANMeasurementConfiguration OPTIONAL,
mDT-Location-Info MDT-Location-Info OPTIONAL,
sensorMeasurementConfiguration SensorMeasurementConfiguration OPTIONAL,
iE-Extensions ProtocolExtensionContainer { { ImmediateMDTNr-ExtIEs} } OPTIONAL,
...
}
ImmediateMDTNr-ExtIEs NGAP-PROTOCOL-EXTENSION ::= {
...
}
InterSystemFailureIndication ::= SEQUENCE {
uERLFReportContainer UERLFReportContainer OPTIONAL,
iE-Extensions ProtocolExtensionContainer { { InterSystemFailureIndication-ExtIEs} } OPTIONAL,
...
}
InterSystemFailureIndication-ExtIEs NGAP-PROTOCOL-EXTENSION ::= {
...
}
IntersystemSONConfigurationTransfer ::= SEQUENCE {
transferType IntersystemSONTransferType,
intersystemSONInformation IntersystemSONInformation,
iE-Extensions ProtocolExtensionContainer { { IntersystemSONConfigurationTransfer-ExtIEs} } OPTIONAL,
...
}
IntersystemSONConfigurationTransfer-ExtIEs NGAP-PROTOCOL-EXTENSION ::= {
...
}
IntersystemSONTransferType ::= CHOICE {
fromEUTRANtoNGRAN FromEUTRANtoNGRAN,
fromNGRANtoEUTRAN FromNGRANtoEUTRAN,
choice-Extensions ProtocolIE-SingleContainer { { IntersystemSONTransferType-ExtIEs} }
}
IntersystemSONTransferType-ExtIEs NGAP-PROTOCOL-IES ::= {
...
}
IntersystemSONeNBID ::= SEQUENCE {
globaleNBID GlobalENB-ID,
selectedEPSTAI EPS-TAI,
iE-Extensions ProtocolExtensionContainer { { IntersystemSONeNBID-ExtIEs} } OPTIONAL,
...
}
IntersystemSONeNBID-ExtIEs NGAP-PROTOCOL-EXTENSION ::= {
...
}
IntersystemSONNGRANnodeID ::= SEQUENCE {
globalRANNodeID GlobalRANNodeID,
selectedTAI TAI,
iE-Extensions ProtocolExtensionContainer { { IntersystemSONNGRANnodeID-ExtIEs} } OPTIONAL,
...
}
IntersystemSONNGRANnodeID-ExtIEs NGAP-PROTOCOL-EXTENSION ::= {
...
}
IntersystemSONInformation ::= CHOICE {
intersystemSONInformationReport IntersystemSONInformationReport,
choice-Extensions ProtocolIE-SingleContainer { { IntersystemSONInformation-ExtIEs} }
}
IntersystemSONInformation-ExtIEs NGAP-PROTOCOL-IES ::= {
{ ID id-IntersystemSONInformationRequest CRITICALITY ignore TYPE IntersystemSONInformationRequest PRESENCE mandatory }|
{ ID id-IntersystemSONInformationReply CRITICALITY ignore TYPE IntersystemSONInformationReply PRESENCE mandatory },
...
}
-- --------------------------------------------------------------------
-- INTER SYSTEM SON INFORMATION REQUEST
-- --------------------------------------------------------------------
IntersystemSONInformationRequest ::= CHOICE {
nGRAN-CellActivation IntersystemCellActivationRequest,
resourceStatus IntersystemResourceStatusRequest,
choice-Extensions ProtocolIE-SingleContainer { { IntersystemSONInformationRequest-ExtIEs} }
}
IntersystemSONInformationRequest-ExtIEs NGAP-PROTOCOL-IES ::= {
...
}
IntersystemCellActivationRequest ::= SEQUENCE {
activationID INTEGER (0..16384, ...),
cellsToActivateList CellsToActivateList,
iE-Extensions ProtocolExtensionContainer { { IntersystemCellActivationRequest-ExtIEs} } OPTIONAL,
...
}
IntersystemCellActivationRequest-ExtIEs NGAP-PROTOCOL-EXTENSION ::= {
...
}
CellsToActivateList ::= SEQUENCE (SIZE(1..maxnoofCellsinNGRANNode)) OF NGRAN-CGI
-- --------------------------------------------------------------------
-- Inter System Resource Status Request
-- --------------------------------------------------------------------
IntersystemResourceStatusRequest ::= SEQUENCE {
reportingSystem ReportingSystem,
reportCharacteristics ReportCharacteristics,
reportType ReportType,
iE-Extensions ProtocolExtensionContainer { { IntersystemResourceStatusRequest-ExtIEs} } OPTIONAL,
...
}
IntersystemResourceStatusRequest-ExtIEs NGAP-PROTOCOL-EXTENSION ::= {
...
}
ReportingSystem ::= CHOICE {
eUTRAN EUTRAN-ReportingSystemIEs,
nGRAN NGRAN-ReportingSystemIEs,
noReporting NULL,
choice-Extensions ProtocolIE-SingleContainer { { ReportingSystem-ExtIEs}}
}
ReportingSystem-ExtIEs NGAP-PROTOCOL-IES ::= {
...
}
EUTRAN-ReportingSystemIEs::= SEQUENCE {
eUTRAN-CellToReportList EUTRAN-CellToReportList,
iE-Extensions ProtocolExtensionContainer { {EUTRAN-ReportingSystemIEs-ExtIEs} } OPTIONAL,
...
}
EUTRAN-ReportingSystemIEs-ExtIEs NGAP-PROTOCOL-EXTENSION ::= {
...
}
NGRAN-ReportingSystemIEs ::= SEQUENCE {
nGRAN-CellToReportList NGRAN-CellToReportList,
iE-Extensions ProtocolExtensionContainer { {NGRAN-ReportingSystemIEs-ExtIEs} } OPTIONAL,
...
}
NGRAN-ReportingSystemIEs-ExtIEs NGAP-PROTOCOL-EXTENSION ::= {
...
}
EUTRAN-CellToReportList ::= SEQUENCE (SIZE(1..maxnoofReportedCells)) OF EUTRAN-CellToReportItem
EUTRAN-CellToReportItem::= SEQUENCE {
eCGI EUTRA-CGI,
iE-Extensions ProtocolExtensionContainer { {EUTRAN-CellToReportItem-ExtIEs} } OPTIONAL,
...
}
EUTRAN-CellToReportItem-ExtIEs NGAP-PROTOCOL-EXTENSION ::= {
...
}
NGRAN-CellToReportList ::= SEQUENCE (SIZE(1.. maxnoofReportedCells)) OF NGRAN-CellToReportItem
NGRAN-CellToReportItem::= SEQUENCE {
nGRAN-CGI NGRAN-CGI,
iE-Extensions ProtocolExtensionContainer { {NGRAN-CellToReportItem-ExtIEs} } OPTIONAL,
...
}
NGRAN-CellToReportItem-ExtIEs NGAP-PROTOCOL-EXTENSION ::= {
...
}
ReportCharacteristics ::= BIT STRING(SIZE(32))
ReportType ::= CHOICE {
eventBasedReporting EventBasedReportingIEs,
periodicReporting PeriodicReportingIEs,
choice-Extensions ProtocolIE-SingleContainer { { ReportType-ExtIEs}}
}
ReportType-ExtIEs NGAP-PROTOCOL-IES ::= {
...
}
EventBasedReportingIEs ::= SEQUENCE {
intersystemResourceThresholdLow IntersystemResourceThreshold,
intersystemResourceThresholdHigh IntersystemResourceThreshold,
numberOfMeasurementReportingLevels NumberOfMeasurementReportingLevels,
iE-Extensions ProtocolExtensionContainer { {EventBasedReportingIEs-ExtIEs} } OPTIONAL,
...
}
EventBasedReportingIEs-ExtIEs NGAP-PROTOCOL-EXTENSION ::= {
...
}
IntersystemResourceThreshold ::= INTEGER(0..100)
NumberOfMeasurementReportingLevels ::= ENUMERATED {n2, n3, n4, n5, n10, ..., n0}
PeriodicReportingIEs ::= SEQUENCE {
reportingPeriodicity ReportingPeriodicity,
iE-Extensions ProtocolExtensionContainer { {PeriodicReportingIEs-ExtIEs} } OPTIONAL,
...
}
PeriodicReportingIEs-ExtIEs NGAP-PROTOCOL-EXTENSION ::= {
...
}
ReportingPeriodicity ::= ENUMERATED {
stop,
single,
ms1000,
ms2000,
ms5000,
ms10000,
...
}
-- --------------------------------------------------------------------
-- INTER SYSTEM SON INFORMATION REPLY
-- --------------------------------------------------------------------
IntersystemSONInformationReply ::= CHOICE {
nGRAN-CellActivation IntersystemCellActivationReply,
resourceStatus IntersystemResourceStatusReply,
choice-Extensions ProtocolIE-SingleContainer { { IntersystemSONInformationReply-ExtIEs} }
}
IntersystemSONInformationReply-ExtIEs NGAP-PROTOCOL-IES ::= {
...
}
IntersystemCellActivationReply ::= SEQUENCE {
activatedCellList ActivatedCellList,
activation-ID INTEGER(0..16384, ...),
iE-Extensions ProtocolExtensionContainer { { IntersystemCellActivationReply-ExtIEs} } OPTIONAL,
...
}
IntersystemCellActivationReply-ExtIEs NGAP-PROTOCOL-EXTENSION ::= {
...
}
ActivatedCellList ::= SEQUENCE (SIZE(1..maxnoofCellsinNGRANNode)) OF NGRAN-CGI
-- --------------------------------------------------------------------
-- Inter System Resource Status Reply
-- --------------------------------------------------------------------
IntersystemResourceStatusReply ::= SEQUENCE {
reportingsystem ReportingSystem,
iE-Extensions ProtocolExtensionContainer { { IntersystemResourceStatusReply-ExtIEs} } OPTIONAL,
...
}
IntersystemResourceStatusReply-ExtIEs NGAP-PROTOCOL-EXTENSION ::= {
...
}
-- --------------------------------------------------------------------
-- INTER SYSTEM SON INFORMATION REPORT
-- --------------------------------------------------------------------
IntersystemSONInformationReport::= CHOICE {
hOReportInformation InterSystemHOReport,
failureIndicationInformation InterSystemFailureIndication,
choice-Extensions ProtocolIE-SingleContainer { { IntersystemSONInformationReport-ExtIEs} }
}
IntersystemSONInformationReport-ExtIEs NGAP-PROTOCOL-IES ::= {
{ ID id-EnergySavingIndication CRITICALITY ignore TYPE IntersystemCellStateIndication PRESENCE mandatory }|
{ ID id-IntersystemResourceStatusUpdate CRITICALITY ignore TYPE IntersystemResourceStatusReport PRESENCE mandatory },
...
}
IntersystemCellStateIndication ::= SEQUENCE {
notificationCellList NotificationCellList,
iE-Extensions ProtocolExtensionContainer { { IntersystemCellStateIndication-ExtIEs} } OPTIONAL,
...
}
IntersystemCellStateIndication-ExtIEs NGAP-PROTOCOL-EXTENSION ::= {
...
}
NotificationCellList ::= SEQUENCE (SIZE(1.. maxnoofCellsinNGRANNode)) OF NotificationCell-Item
NotificationCell-Item ::= SEQUENCE {
nGRAN-CGI NGRAN-CGI,
notifyFlag ENUMERATED {activated, deactivated, ...},
iE-Extensions ProtocolExtensionContainer { { NotificationCell-Item-ExtIEs} } OPTIONAL,
...
}
NotificationCell-Item-ExtIEs NGAP-PROTOCOL-EXTENSION ::= {
...
}
-- --------------------------------------------------------------------
-- Inter System Resource Status Report
-- --------------------------------------------------------------------
IntersystemResourceStatusReport ::= SEQUENCE {
reportingSystem ResourceStatusReportingSystem,
iE-Extensions ProtocolExtensionContainer { { IntersystemResourceStatusReport-ExtIEs} } OPTIONAL,
...
}
IntersystemResourceStatusReport-ExtIEs NGAP-PROTOCOL-EXTENSION ::= {
...
}
ResourceStatusReportingSystem ::= CHOICE {
eUTRAN-ReportingStatus EUTRAN-ReportingStatusIEs,
nGRAN-ReportingStatus NGRAN-ReportingStatusIEs,
choice-Extensions ProtocolIE-SingleContainer { { ResourceStatusReportingSystem-ExtIEs}}
}
ResourceStatusReportingSystem-ExtIEs NGAP-PROTOCOL-IES ::= {
...
}
EUTRAN-ReportingStatusIEs::= SEQUENCE {
eUTRAN-CellReportList EUTRAN-CellReportList,
iE-Extensions ProtocolExtensionContainer { {EUTRAN-ReportingStatusIEs-ExtIEs} } OPTIONAL,
...
}
EUTRAN-ReportingStatusIEs-ExtIEs NGAP-PROTOCOL-EXTENSION ::= {
...
}
EUTRAN-CellReportList ::= SEQUENCE (SIZE(1..maxnoofReportedCells)) OF EUTRAN-CellReportItem
EUTRAN-CellReportItem ::= SEQUENCE {
eCGI EUTRA-CGI,
eUTRAN-CompositeAvailableCapacityGroup EUTRAN-CompositeAvailableCapacityGroup,
eUTRAN-NumberOfActiveUEs EUTRAN-NumberOfActiveUEs OPTIONAL,
eUTRAN-NoofRRCConnections NGRAN-NoofRRCConnections OPTIONAL,
eUTRAN-RadioResourceStatus EUTRAN-RadioResourceStatus OPTIONAL,
iE-Extensions ProtocolExtensionContainer { {EUTRAN-CellReportItem-ExtIEs} } OPTIONAL,
...
}
EUTRAN-CellReportItem-ExtIEs NGAP-PROTOCOL-EXTENSION ::= {
...
}
EUTRAN-CompositeAvailableCapacityGroup ::= SEQUENCE {
dL-CompositeAvailableCapacity CompositeAvailableCapacity,
uL-CompositeAvailableCapacity CompositeAvailableCapacity,
iE-Extensions ProtocolExtensionContainer { { EUTRAN-CompositeAvailableCapacityGroup-ExtIEs} } OPTIONAL,
...
}
EUTRAN-CompositeAvailableCapacityGroup-ExtIEs NGAP-PROTOCOL-EXTENSION ::= {
...
}
CompositeAvailableCapacity ::= SEQUENCE {
cellCapacityClassValue INTEGER (1..100, ...) OPTIONAL,
capacityValue INTEGER (0..100),
iE-Extensions ProtocolExtensionContainer { {CompositeAvailableCapacity-ExtIEs} } OPTIONAL,
...
}
CompositeAvailableCapacity-ExtIEs NGAP-PROTOCOL-EXTENSION ::= {
...
}
EUTRAN-NumberOfActiveUEs ::= INTEGER (0..16777215, ...)
EUTRAN-RadioResourceStatus ::= SEQUENCE {
dL-GBR-PRB-usage INTEGER (0..100),
uL-GBR-PRB-usage INTEGER (0..100),
dL-non-GBR-PRB-usage INTEGER (0..100),
uL-non-GBR-PRB-usage INTEGER (0..100),
dL-Total-PRB-usage INTEGER (0..100),
uL-Total-PRB-usage INTEGER (0..100),
dL-scheduling-PDCCH-CCE-usage INTEGER (0..100) OPTIONAL,
uL-scheduling-PDCCH-CCE-usage INTEGER (0..100) OPTIONAL,
iE-Extensions ProtocolExtensionContainer { {EUTRAN-RadioResourceStatus-ExtIEs} } OPTIONAL,
...
}
EUTRAN-RadioResourceStatus-ExtIEs NGAP-PROTOCOL-EXTENSION ::= {
...
}
NGRAN-ReportingStatusIEs ::= SEQUENCE {
nGRAN-CellReportList NGRAN-CellReportList,
iE-Extensions ProtocolExtensionContainer { {NGRAN-ReportingStatusIEs-ExtIEs} } OPTIONAL,
...
}
NGRAN-ReportingStatusIEs-ExtIEs NGAP-PROTOCOL-EXTENSION ::= {
...
}
NGRAN-CellReportList ::= SEQUENCE (SIZE(1..maxnoofReportedCells)) OF NGRAN-CellReportItem
NGRAN-CellReportItem ::= SEQUENCE {
nGRAN-CGI NGRAN-CGI,
nGRAN-CompositeAvailableCapacityGroup EUTRAN-CompositeAvailableCapacityGroup,
nGRAN-NumberOfActiveUEs NGRAN-NumberOfActiveUEs OPTIONAL,
nGRAN-NoofRRCConnections NGRAN-NoofRRCConnections OPTIONAL,
nGRAN-RadioResourceStatus NGRAN-RadioResourceStatus OPTIONAL,
iE-Extensions ProtocolExtensionContainer { {NGRAN-CellReportItem-ExtIEs} } OPTIONAL,
...
}
NGRAN-CellReportItem-ExtIEs NGAP-PROTOCOL-EXTENSION ::= {
...
}
NGRAN-NumberOfActiveUEs ::= INTEGER (0..16777215, ...)
NGRAN-NoofRRCConnections ::= INTEGER (1..65536, ...)
NGRAN-RadioResourceStatus ::= SEQUENCE {
dL-GBR-PRB-usage-for-MIMO INTEGER (0..100),
uL-GBR-PRB-usage-for-MIMO INTEGER (0..100),
dL-non-GBR-PRB-usage-for-MIMO INTEGER (0..100),
uL-non-GBR-PRB-usage-for-MIMO INTEGER (0..100),
dL-Total-PRB-usage-for-MIMO INTEGER (0..100),
uL-Total-PRB-usage-for-MIMO INTEGER (0..100),
iE-Extensions ProtocolExtensionContainer { { NGRAN-RadioResourceStatus-ExtIEs} } OPTIONAL,
...
}
NGRAN-RadioResourceStatus-ExtIEs NGAP-PROTOCOL-EXTENSION ::= {
...
}
InterSystemHOReport ::= SEQUENCE {
handoverReportType InterSystemHandoverReportType,
iE-Extensions ProtocolExtensionContainer { { InterSystemHOReport-ExtIEs} } OPTIONAL,
...
}
InterSystemHOReport-ExtIEs NGAP-PROTOCOL-EXTENSION ::= {
...
}
InterSystemHandoverReportType ::= CHOICE {
tooearlyIntersystemHO TooearlyIntersystemHO,
intersystemUnnecessaryHO IntersystemUnnecessaryHO,
choice-Extensions ProtocolIE-SingleContainer { { InterSystemHandoverReportType-ExtIEs} }
}
InterSystemHandoverReportType-ExtIEs NGAP-PROTOCOL-IES ::= {
{ ID id-IntersystemMobilityFailureforVoiceFallback CRITICALITY ignore TYPE IntersystemMobilityFailureforVoiceFallback PRESENCE mandatory },
...
}
IntersystemMobilityFailureforVoiceFallback ::= SEQUENCE {
sourcecellID NGRAN-CGI,
targetcellID EUTRA-CGI,
reconnectCellID EUTRA-CGI OPTIONAL,
uERLFReportContainer UERLFReportContainer OPTIONAL,
iE-Extensions ProtocolExtensionContainer { { IntersystemMobilityFailureforVoiceFallback-ExtIEs} } OPTIONAL,
...
}
IntersystemMobilityFailureforVoiceFallback-ExtIEs NGAP-PROTOCOL-EXTENSION ::= {
...
}
IntersystemUnnecessaryHO ::= SEQUENCE {
sourcecellID NGRAN-CGI,
targetcellID EUTRA-CGI,
earlyIRATHO ENUMERATED {true, false, ...},
candidateCellList CandidateCellList,
iE-Extensions ProtocolExtensionContainer { { IntersystemUnnecessaryHO-ExtIEs} } OPTIONAL,
...
}
IntersystemUnnecessaryHO-ExtIEs NGAP-PROTOCOL-EXTENSION ::= {
...
}
-- J
-- K
-- L
LAC ::= OCTET STRING (SIZE (2))
LAI ::= SEQUENCE {
pLMNidentity PLMNIdentity,
lAC LAC,
iE-Extensions ProtocolExtensionContainer { {LAI-ExtIEs} } OPTIONAL,
...
}
LAI-ExtIEs NGAP-PROTOCOL-EXTENSION ::= {
...
}
LastVisitedCellInformation ::= CHOICE {
nGRANCell LastVisitedNGRANCellInformation,
eUTRANCell LastVisitedEUTRANCellInformation,
uTRANCell LastVisitedUTRANCellInformation,
gERANCell LastVisitedGERANCellInformation,
choice-Extensions ProtocolIE-SingleContainer { {LastVisitedCellInformation-ExtIEs} }
}
LastVisitedCellInformation-ExtIEs NGAP-PROTOCOL-IES ::= {
...
}
LastVisitedCellItem ::= SEQUENCE {
lastVisitedCellInformation LastVisitedCellInformation,
iE-Extensions ProtocolExtensionContainer { {LastVisitedCellItem-ExtIEs} } OPTIONAL,
...
}
LastVisitedCellItem-ExtIEs NGAP-PROTOCOL-EXTENSION ::= {
...
}
LastVisitedEUTRANCellInformation ::= OCTET STRING
LastVisitedGERANCellInformation ::= OCTET STRING
LastVisitedNGRANCellInformation::= SEQUENCE {
globalCellID NGRAN-CGI,
cellType CellType,
timeUEStayedInCell TimeUEStayedInCell,
timeUEStayedInCellEnhancedGranularity TimeUEStayedInCellEnhancedGranularity OPTIONAL,
hOCauseValue Cause OPTIONAL,
iE-Extensions ProtocolExtensionContainer { {LastVisitedNGRANCellInformation-ExtIEs} } OPTIONAL,
...
}
LastVisitedNGRANCellInformation-ExtIEs NGAP-PROTOCOL-EXTENSION ::= {
{ ID id-LastVisitedPSCellList CRITICALITY ignore EXTENSION LastVisitedPSCellList PRESENCE optional },
...
}
LastVisitedPSCellList ::= SEQUENCE (SIZE(1..maxnoofPSCellsPerPrimaryCellinUEHistoryInfo)) OF LastVisitedPSCellInformation
LastVisitedPSCellInformation ::= SEQUENCE {
pSCellID NGRAN-CGI OPTIONAL,
timeStay INTEGER (0..40950),
iE-Extensions ProtocolExtensionContainer { {LastVisitedPSCellInformation-ExtIEs} } OPTIONAL,
...
}
LastVisitedPSCellInformation-ExtIEs NGAP-PROTOCOL-EXTENSION ::= {
...
}
LastVisitedUTRANCellInformation ::= OCTET STRING
LineType ::= ENUMERATED {
dsl,
pon,
...
}
LocationReportingAdditionalInfo ::= ENUMERATED {
includePSCell,
...
}
LocationReportingReferenceID ::= INTEGER (1..64, ...)
LocationReportingRequestType ::= SEQUENCE {
eventType EventType,
reportArea ReportArea,
areaOfInterestList AreaOfInterestList OPTIONAL,
locationReportingReferenceIDToBeCancelled LocationReportingReferenceID OPTIONAL,
-- The above IE shall be present if the Event Type IE is set to the value "stop UE presence in the area of interest"
iE-Extensions ProtocolExtensionContainer { {LocationReportingRequestType-ExtIEs} } OPTIONAL,
...
}
LocationReportingRequestType-ExtIEs NGAP-PROTOCOL-EXTENSION ::= {
{ ID id-LocationReportingAdditionalInfo CRITICALITY ignore EXTENSION LocationReportingAdditionalInfo PRESENCE optional }|
{ ID id-AdditionalCancelledlocationReportingReferenceIDList CRITICALITY reject EXTENSION AdditionalCancelledlocationReportingReferenceIDList PRESENCE optional },
...
}
LoggedMDTNr ::= SEQUENCE {
loggingInterval LoggingInterval,
loggingDuration LoggingDuration,
loggedMDTTrigger LoggedMDTTrigger,
bluetoothMeasurementConfiguration BluetoothMeasurementConfiguration OPTIONAL,
wLANMeasurementConfiguration WLANMeasurementConfiguration OPTIONAL,
sensorMeasurementConfiguration SensorMeasurementConfiguration OPTIONAL,
areaScopeOfNeighCellsList AreaScopeOfNeighCellsList OPTIONAL,
iE-Extensions ProtocolExtensionContainer { {LoggedMDTNr-ExtIEs} } OPTIONAL,
...
}
LoggedMDTNr-ExtIEs NGAP-PROTOCOL-EXTENSION ::= {
{ ID id-EarlyMeasurement CRITICALITY ignore EXTENSION EarlyMeasurement PRESENCE optional },
...
}
LoggingInterval ::= ENUMERATED {
ms320, ms640, ms1280, ms2560, ms5120, ms10240, ms20480, ms30720, ms40960, ms61440,
infinity,
...
}
LoggingDuration ::= ENUMERATED {m10, m20, m40, m60, m90, m120, ...}
Links-to-log ::= ENUMERATED {
uplink,
downlink,
both-uplink-and-downlink,
...
}
LoggedMDTTrigger ::= CHOICE{
periodical NULL,
eventTrigger EventTrigger,
choice-Extensions ProtocolIE-SingleContainer { {LoggedMDTTrigger-ExtIEs} }
}
LoggedMDTTrigger-ExtIEs NGAP-PROTOCOL-IES ::= {
...
}
LTEM-Indication ::= ENUMERATED {lte-m,...}
LTEUERLFReportContainer ::= OCTET STRING
LTEV2XServicesAuthorized ::= SEQUENCE {
vehicleUE VehicleUE OPTIONAL,
pedestrianUE PedestrianUE OPTIONAL,
iE-Extensions ProtocolExtensionContainer { {LTEV2XServicesAuthorized-ExtIEs} } OPTIONAL,
...
}
LTEV2XServicesAuthorized-ExtIEs NGAP-PROTOCOL-EXTENSION ::= {
...
}
LTEUESidelinkAggregateMaximumBitrate ::= SEQUENCE {
uESidelinkAggregateMaximumBitRate BitRate,
iE-Extensions ProtocolExtensionContainer { {LTEUE-Sidelink-Aggregate-MaximumBitrates-ExtIEs} } OPTIONAL,
...
}
LTEUE-Sidelink-Aggregate-MaximumBitrates-ExtIEs NGAP-PROTOCOL-EXTENSION ::= {
...
}
LTE-A2X-ServicesAuthorized ::= SEQUENCE {
aerialUE ENUMERATED {authorized, not-authorized, ...} OPTIONAL,
aerialControllerUE ENUMERATED {authorized, not-authorized, ...} OPTIONAL,
iE-Extensions ProtocolExtensionContainer { {LTE-A2X-ServicesAuthorized-ExtIEs} } OPTIONAL,
...
}
LTE-A2X-ServicesAuthorized-ExtIEs NGAP-PROTOCOL-EXTENSION ::= {
...
}
-- M
MaskedIMEISV ::= BIT STRING (SIZE(64))
MaximumDataBurstVolume ::= INTEGER (0..4095, ..., 4096.. 2000000)
MessageIdentifier ::= BIT STRING (SIZE(16))
MaximumIntegrityProtectedDataRate ::= ENUMERATED {
bitrate64kbs,
maximum-UE-rate,
...
}
MBS-AreaSessionID ::= INTEGER (0..65535, ...)
CommServiceType ::= ENUMERATED { mbs-broadcast, mbs-multicast, ... , unicast }
MBS-DataForwardingResponseMRBList ::= SEQUENCE (SIZE(1..maxnoofMRBs)) OF MBS-DataForwardingResponseMRBItem
MBS-DataForwardingResponseMRBItem ::= SEQUENCE {
mRB-ID MRB-ID,
dL-Forwarding-UPTNLInformation UPTransportLayerInformation,
mRB-ProgressInformation MRB-ProgressInformation OPTIONAL,
iE-Extensions ProtocolExtensionContainer { { MBS-DataForwardingResponseMRBItem-ExtIEs} } OPTIONAL,
...
}
MBS-DataForwardingResponseMRBItem-ExtIEs NGAP-PROTOCOL-EXTENSION ::= {
...
}
MBS-MappingandDataForwardingRequestList ::= SEQUENCE (SIZE(1..maxnoofMRBs)) OF MBS-MappingandDataForwardingRequestItem
MBS-MappingandDataForwardingRequestItem ::= SEQUENCE {
mRB-ID MRB-ID,
mBS-QoSFlowList MBS-QoSFlowList,
mRB-ProgressInformation MRB-ProgressInformation OPTIONAL,
iE-Extensions ProtocolExtensionContainer { { MBS-MappingandDataForwardingRequestItem-ExtIEs} } OPTIONAL,
...
}
MBS-MappingandDataForwardingRequestItem-ExtIEs NGAP-PROTOCOL-EXTENSION ::= {
...
}
MBS-QoSFlowList ::= SEQUENCE (SIZE(1..maxnoofMBSQoSFlows)) OF QosFlowIdentifier
MRB-ProgressInformation ::= CHOICE {
pDCP-SN-Length12 INTEGER (0..4095),
pDCP-SN-Length18 INTEGER (0..262143),
choice-Extensions ProtocolIE-SingleContainer { { MRB-ProgressInformation-ExtIEs} }
}
MRB-ProgressInformation-ExtIEs NGAP-PROTOCOL-IES ::= {
...
}
MBS-QoSFlowsToBeSetupList ::= SEQUENCE (SIZE(1.. maxnoofMBSQoSFlows)) OF MBS-QoSFlowsToBeSetupItem
MBS-QoSFlowsToBeSetupItem ::= SEQUENCE {
mBSqosFlowIdentifier QosFlowIdentifier,
mBSqosFlowLevelQosParameters QosFlowLevelQosParameters,
iE-Extensions ProtocolExtensionContainer { {MBS-QoSFlowsToBeSetupItem-ExtIEs} } OPTIONAL,
...
}
MBS-QoSFlowsToBeSetupItem-ExtIEs NGAP-PROTOCOL-EXTENSION ::= {
...
}
MBS-ServiceArea ::= CHOICE {
locationindependent MBS-ServiceAreaInformation,
locationdependent MBS-ServiceAreaInformationList,
choice-Extensions ProtocolIE-SingleContainer { {MBS-ServiceArea-ExtIEs} }
}
MBS-ServiceArea-ExtIEs NGAP-PROTOCOL-IES ::= {
...
}
MBS-ServiceAreaInformationList ::= SEQUENCE (SIZE(1..maxnoofMBSServiceAreaInformation)) OF MBS-ServiceAreaInformationItem
MBS-ServiceAreaInformationItem ::= SEQUENCE {
mBS-AreaSessionID MBS-AreaSessionID,
mBS-ServiceAreaInformation MBS-ServiceAreaInformation,
iE-Extensions ProtocolExtensionContainer { {MBS-ServiceAreaInformationItem-ExtIEs} } OPTIONAL,
...
}
MBS-ServiceAreaInformationItem-ExtIEs NGAP-PROTOCOL-EXTENSION ::= {
...
}
MBS-ServiceAreaInformation ::= SEQUENCE {
mBS-ServiceAreaCellList MBS-ServiceAreaCellList OPTIONAL,
mBS-ServiceAreaTAIList MBS-ServiceAreaTAIList OPTIONAL,
iE-Extensions ProtocolExtensionContainer { {MBS-ServiceAreaInformation-ExtIEs} } OPTIONAL,
...
}
MBS-ServiceAreaInformation-ExtIEs NGAP-PROTOCOL-EXTENSION ::= {
...
}
MBS-ServiceAreaCellList ::= SEQUENCE (SIZE(1.. maxnoofCellsforMBS)) OF NR-CGI
MBS-ServiceAreaTAIList ::= SEQUENCE (SIZE(1.. maxnoofTAIforMBS)) OF TAI
MBS-SessionID ::= SEQUENCE {
tMGI TMGI,
nID NID OPTIONAL,
iE-Extensions ProtocolExtensionContainer { {MBS-SessionID-ExtIEs} } OPTIONAL,
...
}
MBS-SessionID-ExtIEs NGAP-PROTOCOL-EXTENSION ::= {
...
}
MBSSessionFailedtoSetupList ::= SEQUENCE (SIZE(1.. maxnoofMBSSessions)) OF MBSSessionFailedtoSetupItem
MBSSessionFailedtoSetupItem ::= SEQUENCE {
mBS-SessionID MBS-SessionID,
mBS-AreaSessionID MBS-AreaSessionID OPTIONAL,
cause Cause,
iE-Extensions ProtocolExtensionContainer { { MBSSessionFailedtoSetupItem-ExtIEs} } OPTIONAL,
...
}
MBSSessionFailedtoSetupItem-ExtIEs NGAP-PROTOCOL-EXTENSION ::= {
...
}
MBS-ActiveSessionInformation-SourcetoTargetList ::= SEQUENCE (SIZE(1..maxnoofMBSSessionsofUE)) OF MBS-ActiveSessionInformation-SourcetoTargetItem
MBS-ActiveSessionInformation-SourcetoTargetItem ::= SEQUENCE {
mBS-SessionID MBS-SessionID,
mBS-AreaSessionID MBS-AreaSessionID OPTIONAL,
mBS-ServiceArea MBS-ServiceArea OPTIONAL,
mBS-QoSFlowsToBeSetupList MBS-QoSFlowsToBeSetupList,
mBS-MappingandDataForwardingRequestList MBS-MappingandDataForwardingRequestList OPTIONAL,
iE-Extensions ProtocolExtensionContainer { { MBS-ActiveSessionInformation-SourcetoTargetItem-ExtIEs} } OPTIONAL,
...
}
MBS-ActiveSessionInformation-SourcetoTargetItem-ExtIEs NGAP-PROTOCOL-EXTENSION ::= {
...
}
MBS-ActiveSessionInformation-TargettoSourceList ::= SEQUENCE (SIZE(1..maxnoofMBSSessionsofUE)) OF MBS-ActiveSessionInformation-TargettoSourceItem
MBS-ActiveSessionInformation-TargettoSourceItem ::= SEQUENCE {
mBS-SessionID MBS-SessionID,
mBS-DataForwardingResponseMRBList MBS-DataForwardingResponseMRBList OPTIONAL,
iE-Extensions ProtocolExtensionContainer { { MBS-ActiveSessionInformation-TargettoSourceItem-ExtIEs} } OPTIONAL,
...
}
MBS-ActiveSessionInformation-TargettoSourceItem-ExtIEs NGAP-PROTOCOL-EXTENSION ::= {
...
}
MBS-AssistanceInformation ::= ENUMERATED {true, ...}
MBSSessionSetupOrModFailureTransfer ::= SEQUENCE {
cause Cause,
criticalityDiagnostics CriticalityDiagnostics OPTIONAL,
iE-Extensions ProtocolExtensionContainer { { MBSSessionSetupOrModFailureTransfer-ExtIEs} } OPTIONAL,
...
}
MBSSessionSetupOrModFailureTransfer-ExtIEs NGAP-PROTOCOL-EXTENSION ::= {
...
}
MBSSessionSetupResponseList ::= SEQUENCE (SIZE(1.. maxnoofMBSSessions)) OF MBSSessionSetupResponseItem
MBSSessionSetupResponseItem ::= SEQUENCE {
mBS-SessionID MBS-SessionID,
mBS-AreaSessionID MBS-AreaSessionID OPTIONAL,
iE-Extensions ProtocolExtensionContainer { { MBSSessionSetupResponseItem-ExtIEs} } OPTIONAL,
...
}
MBSSessionSetupResponseItem-ExtIEs NGAP-PROTOCOL-EXTENSION ::= {
...
}
MBSSessionSetupOrModRequestTransfer ::= SEQUENCE {
protocolIEs ProtocolIE-Container { {MBSSessionSetupOrModRequestTransferIEs} },
...
}
MBSSessionSetupOrModRequestTransferIEs NGAP-PROTOCOL-IES ::= {
{ ID id-MBS-SessionTNLInfo5GC CRITICALITY reject TYPE MBS-SessionTNLInfo5GC PRESENCE optional }|
{ ID id-MBS-QoSFlowsToBeSetupModList CRITICALITY reject TYPE MBS-QoSFlowsToBeSetupList PRESENCE mandatory }|
{ ID id-MBS-SessionFSAIDList CRITICALITY ignore TYPE MBS-SessionFSAIDList PRESENCE optional }|
{ ID id-SupportedUETypeList CRITICALITY ignore TYPE SupportedUETypeList PRESENCE optional }|
{ ID id-MBS-NGUFailureIndication CRITICALITY reject TYPE MBS-NGUFailureIndication PRESENCE optional },
...
}
SupportedUETypeList ::= SEQUENCE (SIZE(1.. maxnoofUETypes)) OF SupportedUEType
SupportedUEType ::= ENUMERATED {non-RedCap-eRedCap-UE, redCap-eRedCap-UE, ...}
MBS-SessionFSAIDList ::= SEQUENCE (SIZE(1.. maxnoofMBSFSAs)) OF MBS-SessionFSAID
MBS-SessionFSAID ::= OCTET STRING (SIZE(3))
MBSSessionReleaseResponseTransfer ::= SEQUENCE {
mBS-SessionTNLInfoNGRAN MBS-SessionTNLInfoNGRAN OPTIONAL,
iE-Extensions ProtocolExtensionContainer { {MBSSessionReleaseResponseTransfer-ExtIEs} } OPTIONAL,
...
}
MBSSessionReleaseResponseTransfer-ExtIEs NGAP-PROTOCOL-EXTENSION ::= {
...
}
MBSSessionSetupOrModResponseTransfer ::= SEQUENCE {
mBS-SessionTNLInfoNGRAN MBS-SessionTNLInfoNGRAN OPTIONAL,
iE-Extensions ProtocolExtensionContainer { {MBSSessionSetupOrModResponseTransfer-ExtIEs} } OPTIONAL,
...
}
MBSSessionSetupOrModResponseTransfer-ExtIEs NGAP-PROTOCOL-EXTENSION ::= {
...
}
MBS-SupportIndicator ::= ENUMERATED {
multicast-supported,
...,
multicast-supported-with-reception-in-RRC-inactive
}
MBS-SessionTNLInfo5GC ::= CHOICE {
locationindependent SharedNGU-MulticastTNLInformation,
locationdependent MBS-SessionTNLInfo5GCList,
choice-Extensions ProtocolIE-SingleContainer { {MBS-SessionTNLInfo5GC-ExtIEs} }
}
MBS-SessionTNLInfo5GC-ExtIEs NGAP-PROTOCOL-IES ::= {
...
}
MBS-SessionTNLInfo5GCList ::= SEQUENCE (SIZE(1..maxnoofMBSServiceAreaInformation)) OF MBS-SessionTNLInfo5GCItem
MBS-SessionTNLInfo5GCItem ::= SEQUENCE {
mBS-AreaSessionID MBS-AreaSessionID,
sharedNGU-MulticastTNLInformation SharedNGU-MulticastTNLInformation,
iE-Extensions ProtocolExtensionContainer { {MBS-SessionTNLInfo5GCItem-ExtIEs} } OPTIONAL,
...
}
MBS-SessionTNLInfo5GCItem-ExtIEs NGAP-PROTOCOL-EXTENSION ::= {
...
}
MBS-SessionTNLInfoNGRAN ::= CHOICE {
locationindependent UPTransportLayerInformation,
locationdependent MBS-SessionTNLInfoNGRANList,
choice-Extensions ProtocolIE-SingleContainer { {MBS-SessionTNLInfoNGRAN-ExtIEs} }
}
MBS-SessionTNLInfoNGRAN-ExtIEs NGAP-PROTOCOL-IES ::= {
...
}
MBS-SessionTNLInfoNGRANList ::= SEQUENCE (SIZE(1..maxnoofMBSServiceAreaInformation)) OF MBS-SessionTNLInfoNGRANItem
MBS-SessionTNLInfoNGRANItem ::= SEQUENCE {
mBS-AreaSessionID MBS-AreaSessionID,
sharedNGU-UnicastTNLInformation UPTransportLayerInformation OPTIONAL,
iE-Extensions ProtocolExtensionContainer { {MBS-SessionTNLInfoNGRANItem-ExtIEs} } OPTIONAL,
...
}
MBS-SessionTNLInfoNGRANItem-ExtIEs NGAP-PROTOCOL-EXTENSION ::= {
...
}
MBS-DistributionReleaseRequestTransfer ::= SEQUENCE {
mBS-SessionID MBS-SessionID,
mBS-AreaSessionID MBS-AreaSessionID OPTIONAL,
sharedNGU-UnicastTNLInformation UPTransportLayerInformation OPTIONAL,
cause Cause,
iE-Extensions ProtocolExtensionContainer { { MBS-DistributionReleaseRequesTransfer-ExtIEs} } OPTIONAL,
...
}
MBS-DistributionReleaseRequesTransfer-ExtIEs NGAP-PROTOCOL-EXTENSION ::= {
...
}
MBS-DistributionSetupRequestTransfer ::= SEQUENCE {
mBS-SessionID MBS-SessionID,
mBS-AreaSessionID MBS-AreaSessionID OPTIONAL,
sharedNGU-UnicastTNLInformation UPTransportLayerInformation OPTIONAL,
iE-Extensions ProtocolExtensionContainer { { MBS-DistributionSetupRequestTransfer-ExtIEs} } OPTIONAL,
...
}
MBS-DistributionSetupRequestTransfer-ExtIEs NGAP-PROTOCOL-EXTENSION ::= {
{ ID id-TAIMBSSupportList CRITICALITY ignore EXTENSION TAIMBSSupportList PRESENCE optional },
...
}
MBS-DistributionSetupResponseTransfer ::= SEQUENCE {
mBS-SessionID MBS-SessionID,
mBS-AreaSessionID MBS-AreaSessionID OPTIONAL,
sharedNGU-MulticastTNLInformation SharedNGU-MulticastTNLInformation OPTIONAL,
mBS-QoSFlowsToBeSetupList MBS-QoSFlowsToBeSetupList,
mBSSessionStatus MBSSessionStatus,
mBS-ServiceArea MBS-ServiceArea OPTIONAL,
iE-Extensions ProtocolExtensionContainer { {MBS-DistributionSetupResponseTransfer-ExtIEs} } OPTIONAL,
...
}
MBS-DistributionSetupResponseTransfer-ExtIEs NGAP-PROTOCOL-EXTENSION ::= {
...
}
MBS-DistributionSetupUnsuccessfulTransfer ::= SEQUENCE {
mBS-SessionID MBS-SessionID,
mBS-AreaSessionID MBS-AreaSessionID OPTIONAL,
cause Cause,
criticalityDiagnostics CriticalityDiagnostics OPTIONAL,
iE-Extensions ProtocolExtensionContainer { { MBS-DistributionSetupUnsuccessfulTransfer-ExtIEs} } OPTIONAL,
...
}
MBS-DistributionSetupUnsuccessfulTransfer-ExtIEs NGAP-PROTOCOL-EXTENSION ::= {
...
}
MBS-NGUFailureIndication ::= CHOICE {
locationindependent MBS-UP-FailureIndication,
locationdependent MBS-UP-FailureIndicationList,
choice-Extensions ProtocolIE-SingleContainer { {MBS-NGUFailureIndication-ExtIEs} }
}
MBS-NGUFailureIndication-ExtIEs NGAP-PROTOCOL-IES ::= {
...
}
MBS-UP-FailureIndicationList ::= SEQUENCE (SIZE(1..maxnoofMBSServiceAreaInformation)) OF MBS-UP-FailureIndicationItem
MBS-UP-FailureIndicationItem ::= SEQUENCE {
mBS-AreaSessionID MBS-AreaSessionID,
mBS-UP-FailureIndication MBS-UP-FailureIndication,
iE-Extensions ProtocolExtensionContainer { {MBS-UP-FailureIndicationItem-ExtIEs} } OPTIONAL,
...
}
MBS-UP-FailureIndicationItem-ExtIEs NGAP-PROTOCOL-EXTENSION ::= {
...
}
MBS-UP-FailureIndication ::= ENUMERATED {ng-u-path-failure-detected, ...}
MBSSessionSetupRequestList ::= SEQUENCE (SIZE(1..maxnoofMBSSessions)) OF MBSSessionSetupRequestItem
MBSSessionSetupRequestItem ::= SEQUENCE {
mBS-SessionID MBS-SessionID,
mBS-AreaSessionID MBS-AreaSessionID OPTIONAL,
associatedMBSQosFlowSetupRequestList AssociatedMBSQosFlowSetupRequestList OPTIONAL,
iE-Extensions ProtocolExtensionContainer { { MBSSessionSetupRequestItem-ExtIEs} } OPTIONAL,
...
}
MBSSessionSetupRequestItem-ExtIEs NGAP-PROTOCOL-EXTENSION ::= {
{ ID id-MBS-AssistanceInformation CRITICALITY ignore EXTENSION MBS-AssistanceInformation PRESENCE optional },
...
}
MBSSessionSetuporModifyRequestList ::= SEQUENCE (SIZE(1..maxnoofMBSSessions)) OF MBSSessionSetuporModifyRequestItem
MBSSessionSetuporModifyRequestItem ::= SEQUENCE {
mBS-SessionID MBS-SessionID,
mBS-AreaSessionID MBS-AreaSessionID OPTIONAL,
associatedMBSQosFlowSetuporModifyRequestList AssociatedMBSQosFlowSetuporModifyRequestList OPTIONAL,
mBS-QosFlowToReleaseList QosFlowListWithCause OPTIONAL,
iE-Extensions ProtocolExtensionContainer {{MBSSessionSetuporModifyRequestItem-ExtIEs}} OPTIONAL,
...
}
MBSSessionSetuporModifyRequestItem-ExtIEs NGAP-PROTOCOL-EXTENSION ::= {
{ ID id-MBS-AssistanceInformation CRITICALITY ignore EXTENSION MBS-AssistanceInformation PRESENCE optional },
...
}
MBSSessionToReleaseList ::= SEQUENCE (SIZE(1..maxnoofMBSSessions)) OF MBSSessionToReleaseItem
MBSSessionToReleaseItem ::= SEQUENCE {
mBS-SessionID MBS-SessionID,
cause Cause,
iE-Extensions ProtocolExtensionContainer { { MBSSessionToReleaseItem-ExtIEs} } OPTIONAL,
...
}
MBSSessionToReleaseItem-ExtIEs NGAP-PROTOCOL-EXTENSION ::= {
...
}
MBSSessionStatus ::= ENUMERATED {
activated,
deactivated,
...
}
MicoAllPLMN ::= ENUMERATED {
true,
...
}
MICOModeIndication ::= ENUMERATED {
true,
...
}
MobilityInformation ::= BIT STRING (SIZE(16))
ExtendedMobilityInformation ::= BIT STRING (SIZE(32))
MobilityRestrictionList ::= SEQUENCE {
servingPLMN PLMNIdentity,
equivalentPLMNs EquivalentPLMNs OPTIONAL,
rATRestrictions RATRestrictions OPTIONAL,
forbiddenAreaInformation ForbiddenAreaInformation OPTIONAL,
serviceAreaInformation ServiceAreaInformation OPTIONAL,
iE-Extensions ProtocolExtensionContainer { {MobilityRestrictionList-ExtIEs} } OPTIONAL,
...
}
MobilityRestrictionList-ExtIEs NGAP-PROTOCOL-EXTENSION ::= {
{ ID id-LastEUTRAN-PLMNIdentity CRITICALITY ignore EXTENSION PLMNIdentity PRESENCE optional }|
{ ID id-CNTypeRestrictionsForServing CRITICALITY ignore EXTENSION CNTypeRestrictionsForServing PRESENCE optional }|
{ ID id-CNTypeRestrictionsForEquivalent CRITICALITY ignore EXTENSION CNTypeRestrictionsForEquivalent PRESENCE optional }|
{ ID id-NPN-MobilityInformation CRITICALITY reject EXTENSION NPN-MobilityInformation PRESENCE optional },
...
}
MDT-AlignmentInfo ::= CHOICE {
s-basedMDT NGRANTraceID,
choice-Extensions ProtocolIE-SingleContainer { { MDT-AlignmentInfo-ExtIEs} }
}
MDT-AlignmentInfo-ExtIEs NGAP-PROTOCOL-IES ::= {
...
}
MDTPLMNList ::= SEQUENCE (SIZE(1..maxnoofMDTPLMNs)) OF PLMNIdentity
MDTPLMNModificationList ::= SEQUENCE (SIZE(0..maxnoofMDTPLMNs)) OF PLMNIdentity
MDT-Configuration ::= SEQUENCE {
mdt-Config-NR MDT-Configuration-NR OPTIONAL,
mdt-Config-EUTRA MDT-Configuration-EUTRA OPTIONAL,
iE-Extensions ProtocolExtensionContainer { { MDT-Configuration-ExtIEs} } OPTIONAL,
...
}
MDT-Configuration-ExtIEs NGAP-PROTOCOL-EXTENSION ::= {
{ ID id-MN-only-MDT-collection CRITICALITY ignore EXTENSION MN-only-MDT-collection PRESENCE optional },
...
}
MN-only-MDT-collection ::= ENUMERATED {mn-only, ...}
MDT-Configuration-NR ::= SEQUENCE {
mdt-Activation MDT-Activation,
areaScopeOfMDT AreaScopeOfMDT-NR,
mDTModeNr MDTModeNr,
signallingBasedMDTPLMNList MDTPLMNList OPTIONAL,
iE-Extensions ProtocolExtensionContainer { { MDT-Configuration-NR-ExtIEs} } OPTIONAL,
...
}
MDT-Configuration-NR-ExtIEs NGAP-PROTOCOL-EXTENSION ::= {
{ ID id-PNI-NPN-AreaScopeofMDT CRITICALITY ignore EXTENSION PNI-NPN-AreaScopeofMDT PRESENCE optional },
...
}
MDT-Configuration-EUTRA ::= SEQUENCE {
mdt-Activation MDT-Activation,
areaScopeOfMDT AreaScopeOfMDT-EUTRA,
mDTMode MDTModeEutra,
signallingBasedMDTPLMNList MDTPLMNList OPTIONAL,
iE-Extensions ProtocolExtensionContainer { { MDT-Configuration-EUTRA-ExtIEs} } OPTIONAL,
...
}
MDT-Configuration-EUTRA-ExtIEs NGAP-PROTOCOL-EXTENSION ::= {
...
}
MDT-Activation ::= ENUMERATED {
immediate-MDT-only,
logged-MDT-only,
immediate-MDT-and-Trace,
...
}
MDTModeNr ::= CHOICE {
immediateMDTNr ImmediateMDTNr,
loggedMDTNr LoggedMDTNr,
choice-Extensions ProtocolIE-SingleContainer { {MDTModeNr-ExtIEs} }
}
MDTModeNr-ExtIEs NGAP-PROTOCOL-IES ::= {
...
}
MDTModeEutra ::= OCTET STRING
MeasurementsToActivate ::= BIT STRING(SIZE(8))
MobileIAB-Authorized ::= ENUMERATED {
authorized,
not-authorized,
...
}
MobileIABNodeIndication ::= ENUMERATED {
true,
...
}
MobileIAB-Supported ::= ENUMERATED {
true,
...
}
MRB-ID ::= INTEGER (1..512, ...)
MulticastSessionActivationRequestTransfer ::= SEQUENCE {
mBS-SessionID MBS-SessionID,
iE-Extensions ProtocolExtensionContainer { { MulticastSessionActivationRequestTransfer-ExtIEs} } OPTIONAL,
...
}
MulticastSessionActivationRequestTransfer-ExtIEs NGAP-PROTOCOL-EXTENSION ::= {
...
}
MulticastSessionDeactivationRequestTransfer ::= SEQUENCE {
mBS-SessionID MBS-SessionID,
iE-Extensions ProtocolExtensionContainer { { MulticastSessionDeactivationRequestTransfer-ExtIEs} } OPTIONAL,
...
}
MulticastSessionDeactivationRequestTransfer-ExtIEs NGAP-PROTOCOL-EXTENSION ::= {
...
}
MulticastSessionUpdateRequestTransfer ::= SEQUENCE {
protocolIEs ProtocolIE-Container { {MulticastSessionUpdateRequestTransferIEs} },
...
}
MulticastSessionUpdateRequestTransferIEs NGAP-PROTOCOL-IES ::= {
{ ID id-MBS-SessionID CRITICALITY reject TYPE MBS-SessionID PRESENCE mandatory }|
{ ID id-MBS-ServiceArea CRITICALITY reject TYPE MBS-ServiceArea PRESENCE optional }|
{ ID id-MBS-QoSFlowsToBeSetupModList CRITICALITY reject TYPE MBS-QoSFlowsToBeSetupList PRESENCE optional }|
{ ID id-MBS-QoSFlowToReleaseList CRITICALITY reject TYPE QosFlowListWithCause PRESENCE optional }|
{ ID id-MBS-SessionTNLInfo5GC CRITICALITY reject TYPE MBS-SessionTNLInfo5GC PRESENCE optional },
...
}
MulticastGroupPagingAreaList ::= SEQUENCE (SIZE(1..maxnoofPagingAreas)) OF MulticastGroupPagingAreaItem
MulticastGroupPagingAreaItem ::= SEQUENCE {
multicastGroupPagingArea MulticastGroupPagingArea,
uE-PagingList UE-PagingList OPTIONAL,
iE-Extensions ProtocolExtensionContainer { { MulticastGroupPagingAreaItem-ExtIEs} } OPTIONAL,
...
}
MulticastGroupPagingAreaItem-ExtIEs NGAP-PROTOCOL-EXTENSION ::= {
...
}
MBS-AreaTAIList ::= SEQUENCE (SIZE(1..maxnoofTAIforPaging)) OF TAI
MulticastGroupPagingArea ::= SEQUENCE {
mBS-AreaTAIList MBS-AreaTAIList,
iE-Extensions ProtocolExtensionContainer { { MulticastGroupPagingArea-ExtIEs} } OPTIONAL,
...
}
MulticastGroupPagingArea-ExtIEs NGAP-PROTOCOL-EXTENSION ::= {
...
}
UE-PagingList ::= SEQUENCE (SIZE(1..maxnoofUEsforPaging)) OF UE-PagingItem
UE-PagingItem ::= SEQUENCE {
uEIdentityIndexValue UEIdentityIndexValue,
pagingDRX PagingDRX OPTIONAL,
iE-Extensions ProtocolExtensionContainer { { UE-PagingItem-ExtIEs} } OPTIONAL,
...
}
UE-PagingItem-ExtIEs NGAP-PROTOCOL-EXTENSION ::= {
...
}
M1Configuration ::= SEQUENCE {
m1reportingTrigger M1ReportingTrigger,
m1thresholdEventA2 M1ThresholdEventA2 OPTIONAL,
-- The above IE shall be present if the M1 Reporting Trigger IE is set to the value "A2event-triggered" or "A2event-triggered periodic"
m1periodicReporting M1PeriodicReporting OPTIONAL,
-- The above IE shall be present if the M1 Reporting Trigger IE is set to the value "periodic" or "A2event-triggered periodic"
iE-Extensions ProtocolExtensionContainer { { M1Configuration-ExtIEs} } OPTIONAL,
...
}
M1Configuration-ExtIEs NGAP-PROTOCOL-EXTENSION ::= {
{ ID id-IncludeBeamMeasurementsIndication CRITICALITY ignore EXTENSION IncludeBeamMeasurementsIndication PRESENCE optional }|
{ ID id-BeamMeasurementsReportConfiguration CRITICALITY ignore EXTENSION BeamMeasurementsReportConfiguration PRESENCE conditional },
-- The above IE shall be present if the Include Beam Measurements Indication IE is set to the value "true"
...
}
IncludeBeamMeasurementsIndication ::= ENUMERATED {
true,
...
}
MaxNrofRS-IndexesToReport ::= INTEGER (1..64, ...)
M1ReportingTrigger ::= ENUMERATED {
periodic,
a2eventtriggered,
a2eventtriggered-periodic,
...
}
M1ThresholdEventA2 ::= SEQUENCE {
m1ThresholdType M1ThresholdType,
iE-Extensions ProtocolExtensionContainer { { M1ThresholdEventA2-ExtIEs} } OPTIONAL,
...
}
M1ThresholdEventA2-ExtIEs NGAP-PROTOCOL-EXTENSION ::= {
...
}
M1ThresholdType ::= CHOICE {
threshold-RSRP Threshold-RSRP,
threshold-RSRQ Threshold-RSRQ,
threshold-SINR Threshold-SINR,
choice-Extensions ProtocolIE-SingleContainer { {M1ThresholdType-ExtIEs} }
}
M1ThresholdType-ExtIEs NGAP-PROTOCOL-IES ::= {
...
}
M1PeriodicReporting ::= SEQUENCE {
reportInterval ReportIntervalMDT,
reportAmount ReportAmountMDT,
iE-Extensions ProtocolExtensionContainer { { M1PeriodicReporting-ExtIEs} } OPTIONAL,
...
}
M1PeriodicReporting-ExtIEs NGAP-PROTOCOL-EXTENSION ::= {
{ID id-ExtendedReportIntervalMDT CRITICALITY ignore EXTENSION ExtendedReportIntervalMDT PRESENCE optional},
...
}
M4Configuration ::= SEQUENCE {
m4period M4period,
m4-links-to-log Links-to-log,
iE-Extensions ProtocolExtensionContainer { { M4Configuration-ExtIEs} } OPTIONAL,
...
}
M4Configuration-ExtIEs NGAP-PROTOCOL-EXTENSION ::= {
{ ID id-M4ReportAmount CRITICALITY ignore EXTENSION M4ReportAmountMDT PRESENCE optional },
...
}
M4ReportAmountMDT ::= ENUMERATED {r1, r2, r4, r8, r16, r32, r64, infinity, ...}
M4period ::= ENUMERATED {ms1024, ms2048, ms5120, ms10240, min1, ... }
M5Configuration ::= SEQUENCE {
m5period M5period,
m5-links-to-log Links-to-log,
iE-Extensions ProtocolExtensionContainer { { M5Configuration-ExtIEs} } OPTIONAL,
...
}
M5Configuration-ExtIEs NGAP-PROTOCOL-EXTENSION ::= {
{ ID id-M5ReportAmount CRITICALITY ignore EXTENSION M5ReportAmountMDT PRESENCE optional },
...
}
M5ReportAmountMDT ::= ENUMERATED {r1, r2, r4, r8, r16, r32, r64, infinity, ...}
M5period ::= ENUMERATED {ms1024, ms2048, ms5120, ms10240, min1, ... }
M6Configuration ::= SEQUENCE {
m6report-Interval M6report-Interval,
m6-links-to-log Links-to-log,
iE-Extensions ProtocolExtensionContainer { { M6Configuration-ExtIEs} } OPTIONAL,
...
}
M6Configuration-ExtIEs NGAP-PROTOCOL-EXTENSION ::= {
{ ID id-M6ReportAmount CRITICALITY ignore EXTENSION M6ReportAmountMDT PRESENCE optional }|
{ ID id-ExcessPacketDelayThresholdConfiguration CRITICALITY ignore EXTENSION ExcessPacketDelayThresholdConfiguration PRESENCE optional },
...
}
M6ReportAmountMDT ::= ENUMERATED {r1, r2, r4, r8, r16, r32, r64, infinity, ...}
M6report-Interval ::= ENUMERATED {
ms120, ms240, ms480, ms640, ms1024, ms2048, ms5120, ms10240, ms20480, ms40960, min1, min6, min12, min30,
...
}
M7Configuration ::= SEQUENCE {
m7period M7period,
m7-links-to-log Links-to-log,
iE-Extensions ProtocolExtensionContainer { { M7Configuration-ExtIEs} } OPTIONAL,
...
}
M7Configuration-ExtIEs NGAP-PROTOCOL-EXTENSION ::= {
{ ID id-M7ReportAmount CRITICALITY ignore EXTENSION M7ReportAmountMDT PRESENCE optional },
...
}
M7ReportAmountMDT ::= ENUMERATED {r1, r2, r4, r8, r16, r32, r64, infinity, ...}
M7period ::= INTEGER(1..60, ...)
MDT-Location-Info ::= SEQUENCE {
mDT-Location-Information MDT-Location-Information,
iE-Extensions ProtocolExtensionContainer { { MDT-Location-Info-ExtIEs} } OPTIONAL,
...
}
MDT-Location-Info-ExtIEs NGAP-PROTOCOL-EXTENSION ::= {
...
}
MDT-Location-Information::= BIT STRING (SIZE (8))
-- N
N3IWF-ID ::= CHOICE {
n3IWF-ID BIT STRING (SIZE(16)),
choice-Extensions ProtocolIE-SingleContainer { {N3IWF-ID-ExtIEs} }
}
N3IWF-ID-ExtIEs NGAP-PROTOCOL-IES ::= {
...
}
N6JitterInformation ::= SEQUENCE {
n6JitterLowerBound INTEGER (-127..127),
n6JitterUpperBound INTEGER (-127..127),
iE-Extensions ProtocolExtensionContainer { { N6JitterInformation-ExtIEs} } OPTIONAL,
...
}
N6JitterInformation-ExtIEs NGAP-PROTOCOL-EXTENSION ::= {
...
}
NAS-PDU ::= OCTET STRING
NASSecurityParametersFromNGRAN ::= OCTET STRING
NB-IoT-DefaultPagingDRX ::= ENUMERATED {
rf128, rf256, rf512, rf1024,
...
}
NB-IoT-PagingDRX ::= ENUMERATED {
rf32, rf64, rf128, rf256, rf512, rf1024,
...
}
NB-IoT-Paging-eDRXCycle ::= ENUMERATED {
hf2, hf4, hf6, hf8, hf10, hf12, hf14, hf16, hf32, hf64, hf128, hf256, hf512, hf1024,
...
}
NB-IoT-Paging-TimeWindow ::= ENUMERATED {
s1, s2, s3, s4, s5, s6, s7, s8, s9, s10, s11, s12, s13, s14, s15, s16,
...
}
NB-IoT-Paging-eDRXInfo ::= SEQUENCE {
nB-IoT-Paging-eDRXCycle NB-IoT-Paging-eDRXCycle,
nB-IoT-Paging-TimeWindow NB-IoT-Paging-TimeWindow OPTIONAL,
iE-Extensions ProtocolExtensionContainer { { NB-IoT-Paging-eDRXInfo-ExtIEs} } OPTIONAL,
...
}
NB-IoT-Paging-eDRXInfo-ExtIEs NGAP-PROTOCOL-EXTENSION ::= {
...
}
NB-IoT-UEPriority ::= INTEGER (0..255, ...)
NetworkControlledRepeaterAuthorized ::= ENUMERATED {authorized, not-authorized, ...}
NetworkInstance ::= INTEGER (1..256, ...)
NewSecurityContextInd ::= ENUMERATED {
true,
...
}
NextHopChainingCount ::= INTEGER (0..7)
NextPagingAreaScope ::= ENUMERATED {
same,
changed,
...
}
NGAPIESupportInformationRequestList ::= SEQUENCE (SIZE(1.. maxnoofNGAPIESupportInfo)) OF NGAPIESupportInformationRequestItem
NGAPIESupportInformationRequestItem ::= SEQUENCE {
ngap-ProtocolIE-Id ProtocolIE-ID,
iE-Extensions ProtocolExtensionContainer { { NGAPIESupportInformationRequestItem-ExtIEs} } OPTIONAL,
...
}
NGAPIESupportInformationRequestItem-ExtIEs NGAP-PROTOCOL-EXTENSION ::= {
...
}
NGAPIESupportInformationResponseList ::= SEQUENCE (SIZE(1.. maxnoofNGAPIESupportInfo)) OF NGAPIESupportInformationResponseItem
NGAPIESupportInformationResponseItem ::= SEQUENCE {
ngap-ProtocolIE-Id ProtocolIE-ID,
ngap-ProtocolIESupportInfo ENUMERATED {supported, not-supported, ...},
ngap-ProtocolIEPresenceInfo ENUMERATED {present, not-present, ...},
iE-Extensions ProtocolExtensionContainer { { NGAPIESupportInformationResponseItem-ExtIEs} } OPTIONAL,
...
}
NGAPIESupportInformationResponseItem-ExtIEs NGAP-PROTOCOL-EXTENSION ::= {
...
}
NgENB-ID ::= CHOICE {
macroNgENB-ID BIT STRING (SIZE(20)),
shortMacroNgENB-ID BIT STRING (SIZE(18)),
longMacroNgENB-ID BIT STRING (SIZE(21)),
choice-Extensions ProtocolIE-SingleContainer { {NgENB-ID-ExtIEs} }
}
NgENB-ID-ExtIEs NGAP-PROTOCOL-IES ::= {
...
}
NotifySourceNGRANNode ::= ENUMERATED {
notifySource,
...
}
NGRAN-CGI ::= CHOICE {
nR-CGI NR-CGI,
eUTRA-CGI EUTRA-CGI,
choice-Extensions ProtocolIE-SingleContainer { {NGRAN-CGI-ExtIEs} }
}
NGRAN-CGI-ExtIEs NGAP-PROTOCOL-IES ::= {
...
}
NGRAN-TNLAssociationToRemoveList ::= SEQUENCE (SIZE(1..maxnoofTNLAssociations)) OF NGRAN-TNLAssociationToRemoveItem
NGRAN-TNLAssociationToRemoveItem::= SEQUENCE {
tNLAssociationTransportLayerAddress CPTransportLayerInformation,
tNLAssociationTransportLayerAddressAMF CPTransportLayerInformation OPTIONAL,
iE-Extensions ProtocolExtensionContainer { { NGRAN-TNLAssociationToRemoveItem-ExtIEs} } OPTIONAL
}
NGRAN-TNLAssociationToRemoveItem-ExtIEs NGAP-PROTOCOL-EXTENSION ::= {
...
}
NGRANTraceID ::= OCTET STRING (SIZE(8))
NID ::= BIT STRING (SIZE(44))
NonDynamic5QIDescriptor ::= SEQUENCE {
fiveQI FiveQI,
priorityLevelQos PriorityLevelQos OPTIONAL,
averagingWindow AveragingWindow OPTIONAL,
maximumDataBurstVolume MaximumDataBurstVolume OPTIONAL,
iE-Extensions ProtocolExtensionContainer { {NonDynamic5QIDescriptor-ExtIEs} } OPTIONAL,
...
}
NonDynamic5QIDescriptor-ExtIEs NGAP-PROTOCOL-EXTENSION ::= {
{ ID id-CNPacketDelayBudgetDL CRITICALITY ignore EXTENSION ExtendedPacketDelayBudget PRESENCE optional }|
{ ID id-CNPacketDelayBudgetUL CRITICALITY ignore EXTENSION ExtendedPacketDelayBudget PRESENCE optional },
...
}
NoPDUSessionIndication ::= ENUMERATED {true, ...}
NotAllowedTACs ::= SEQUENCE (SIZE(1..maxnoofAllowedAreas)) OF TAC
NotificationCause ::= ENUMERATED {
fulfilled,
not-fulfilled,
...
}
NotificationControl ::= ENUMERATED {
notification-requested,
...
}
NPN-AccessInformation ::= CHOICE {
pNI-NPN-Access-Information CellCAGList,
choice-Extensions ProtocolIE-SingleContainer { {NPN-AccessInformation-ExtIEs} }
}
NPN-AccessInformation-ExtIEs NGAP-PROTOCOL-IES ::= {
...
}
NPN-MobilityInformation ::= CHOICE {
sNPN-MobilityInformation SNPN-MobilityInformation,
pNI-NPN-MobilityInformation PNI-NPN-MobilityInformation,
choice-Extensions ProtocolIE-SingleContainer { {NPN-MobilityInformation-ExtIEs} }
}
NPN-MobilityInformation-ExtIEs NGAP-PROTOCOL-IES ::= {
...
}
NPN-PagingAssistanceInformation ::= CHOICE {
pNI-NPN-PagingAssistance Allowed-PNI-NPN-List,
choice-Extensions ProtocolIE-SingleContainer { {NPN-PagingAssistanceInformation-ExtIEs} }
}
NPN-PagingAssistanceInformation-ExtIEs NGAP-PROTOCOL-IES ::= {
...
}
NPN-Support ::= CHOICE {
sNPN NID,
choice-Extensions ProtocolIE-SingleContainer { {NPN-Support-ExtIEs} }
}
NPN-Support-ExtIEs NGAP-PROTOCOL-IES ::= {
...
}
NRCellIdentity ::= BIT STRING (SIZE(36))
NR-CGI ::= SEQUENCE {
pLMNIdentity PLMNIdentity,
nRCellIdentity NRCellIdentity,
iE-Extensions ProtocolExtensionContainer { {NR-CGI-ExtIEs} } OPTIONAL,
...
}
NR-CGI-ExtIEs NGAP-PROTOCOL-EXTENSION ::= {
...
}
NR-CGIList ::= SEQUENCE (SIZE(1..maxnoofCellsingNB)) OF NR-CGI
NR-CGIListForWarning ::= SEQUENCE (SIZE(1..maxnoofCellIDforWarning)) OF NR-CGI
NR-PagingeDRXInformation ::= SEQUENCE {
nR-paging-eDRX-Cycle NR-Paging-eDRX-Cycle,
nR-paging-Time-Window NR-Paging-Time-Window OPTIONAL,
iE-Extensions ProtocolExtensionContainer { {NR-PagingeDRXInformation-ExtIEs} } OPTIONAL,
...
}
NR-PagingeDRXInformation-ExtIEs NGAP-PROTOCOL-EXTENSION ::= {
...
}
NR-Paging-eDRX-Cycle ::= ENUMERATED {
hfquarter, hfhalf, hf1, hf2, hf4, hf8, hf16,
hf32, hf64, hf128, hf256, hf512, hf1024,
...
}
NR-Paging-Long-eDRX-Information-for-RRC-INACTIVE ::= SEQUENCE {
nR-paging-Long-eDRX-Cycle-for-RRC-INACTIVE NR-Paging-Long-eDRX-Cycle-for-RRC-INACTIVE,
nR-paging-Time-Window-for-RRC-INACTIVE NR-Paging-Time-Window-for-RRC-INACTIVE,
iE-Extensions ProtocolExtensionContainer { {NR-Paging-Long-eDRX-Information-for-RRC-INACTIVE-ExtIEs} } OPTIONAL,
...
}
NR-Paging-Long-eDRX-Information-for-RRC-INACTIVE-ExtIEs NGAP-PROTOCOL-EXTENSION ::= {
...
}
NR-Paging-Long-eDRX-Cycle-for-RRC-INACTIVE ::= ENUMERATED {
hf2, hf4, hf8, hf16,
hf32, hf64, hf128, hf256, hf512, hf1024,
...
}
NR-Paging-Time-Window ::= ENUMERATED {
s1, s2, s3, s4, s5,
s6, s7, s8, s9, s10,
s11, s12, s13, s14, s15, s16,
...,
s17, s18, s19, s20, s21, s22, s23, s24,
s25, s26, s27, s28, s29, s30, s31, s32
}
NR-Paging-Time-Window-for-RRC-INACTIVE ::= ENUMERATED {
s1, s2, s3, s4, s5,
s6, s7, s8, s9, s10,
s11, s12, s13, s14, s15, s16,
s17, s18, s19, s20, s21, s22, s23, s24,
s25, s26, s27, s28, s29, s30, s31, s32,
...
}
NRencryptionAlgorithms ::= BIT STRING (SIZE(16, ...))
NRintegrityProtectionAlgorithms ::= BIT STRING (SIZE(16, ...))
NRMobilityHistoryReport ::= OCTET STRING
NRPPa-PDU ::= OCTET STRING
NRUERLFReportContainer ::= OCTET STRING
NRNTNTAIInformation ::= SEQUENCE {
servingPLMN PLMNIdentity,
tACListInNRNTN TACListInNRNTN,
uELocationDerivedTACInNRNTN TAC OPTIONAL,
iE-Extensions ProtocolExtensionContainer { { NRNTNTAIInformation-ExtIEs} } OPTIONAL,
...
}
NRNTNTAIInformation-ExtIEs NGAP-PROTOCOL-EXTENSION ::= {
...
}
NumberOfBroadcasts ::= INTEGER (0..65535)
NumberOfBroadcastsRequested ::= INTEGER (0..65535)
NRARFCN ::= INTEGER (0.. maxNRARFCN)
NRFrequencyBand ::= INTEGER (1..1024, ...)
NRFrequencyBand-List ::= SEQUENCE (SIZE(1..maxnoofNRCellBands)) OF NRFrequencyBandItem
NRFrequencyBandItem ::= SEQUENCE {
nr-frequency-band NRFrequencyBand,
iE-Extension ProtocolExtensionContainer { {NRFrequencyBandItem-ExtIEs} } OPTIONAL,
...
}
NRFrequencyBandItem-ExtIEs NGAP-PROTOCOL-EXTENSION ::= {
...
}
NRFrequencyInfo ::= SEQUENCE {
nrARFCN NRARFCN,
frequencyBand-List NRFrequencyBand-List,
iE-Extension ProtocolExtensionContainer { {NRFrequencyInfo-ExtIEs} } OPTIONAL,
...
}
NRFrequencyInfo-ExtIEs NGAP-PROTOCOL-EXTENSION ::= {
...
}
NR-PCI ::= INTEGER (0..1007, ...)
NRV2XServicesAuthorized ::= SEQUENCE {
vehicleUE VehicleUE OPTIONAL,
pedestrianUE PedestrianUE OPTIONAL,
iE-Extensions ProtocolExtensionContainer { {NRV2XServicesAuthorized-ExtIEs} } OPTIONAL,
...
}
NRV2XServicesAuthorized-ExtIEs NGAP-PROTOCOL-EXTENSION ::= {
...
}
VehicleUE ::= ENUMERATED {
authorized,
not-authorized,
...
}
PedestrianUE ::= ENUMERATED {
authorized,
not-authorized,
...
}
NRUESidelinkAggregateMaximumBitrate ::= SEQUENCE {
uESidelinkAggregateMaximumBitRate BitRate,
iE-Extensions ProtocolExtensionContainer { {NRUESidelinkAggregateMaximumBitrate-ExtIEs} } OPTIONAL,
...
}
NRUESidelinkAggregateMaximumBitrate-ExtIEs NGAP-PROTOCOL-EXTENSION ::= {
...
}
NSAG-ID ::= INTEGER (0..255, ...)
NR-A2X-ServicesAuthorized ::= SEQUENCE {
aerialUE ENUMERATED {authorized, not-authorized, ...} OPTIONAL,
aerialControllerUE ENUMERATED {authorized, not-authorized, ...} OPTIONAL,
iE-Extensions ProtocolExtensionContainer { {NR-A2X-ServicesAuthorized-ExtIEs} } OPTIONAL,
...
}
NR-A2X-ServicesAuthorized-ExtIEs NGAP-PROTOCOL-EXTENSION ::= {
...
}
-- O
OnboardingSupport ::= ENUMERATED {
true,
...
}
OverloadAction ::= ENUMERATED {
reject-non-emergency-mo-dt,
reject-rrc-cr-signalling,
permit-emergency-sessions-and-mobile-terminated-services-only,
permit-high-priority-sessions-and-mobile-terminated-services-only,
...
}
OverloadResponse ::= CHOICE {
overloadAction OverloadAction,
choice-Extensions ProtocolIE-SingleContainer { {OverloadResponse-ExtIEs} }
}
OverloadResponse-ExtIEs NGAP-PROTOCOL-IES ::= {
...
}
OverloadStartNSSAIList ::= SEQUENCE (SIZE (1..maxnoofSliceItems)) OF OverloadStartNSSAIItem
OverloadStartNSSAIItem ::= SEQUENCE {
sliceOverloadList SliceOverloadList,
sliceOverloadResponse OverloadResponse OPTIONAL,
sliceTrafficLoadReductionIndication TrafficLoadReductionIndication OPTIONAL,
iE-Extensions ProtocolExtensionContainer { {OverloadStartNSSAIItem-ExtIEs} } OPTIONAL,
...
}
OverloadStartNSSAIItem-ExtIEs NGAP-PROTOCOL-EXTENSION ::= {
...
}
-- P
PacketDelayBudget ::= INTEGER (0..1023, ...)
PacketErrorRate ::= SEQUENCE {
pERScalar INTEGER (0..9, ...),
pERExponent INTEGER (0..9, ...),
iE-Extensions ProtocolExtensionContainer { {PacketErrorRate-ExtIEs} } OPTIONAL,
...
}
PacketErrorRate-ExtIEs NGAP-PROTOCOL-EXTENSION ::= {
...
}
PacketLossRate ::= INTEGER (0..1000, ...)
PagingAssisDataforCEcapabUE ::= SEQUENCE {
eUTRA-CGI EUTRA-CGI,
coverageEnhancementLevel CoverageEnhancementLevel,
iE-Extensions ProtocolExtensionContainer { { PagingAssisDataforCEcapabUE-ExtIEs} } OPTIONAL,
...
}
PagingAssisDataforCEcapabUE-ExtIEs NGAP-PROTOCOL-EXTENSION ::= {
...
}
PagingAttemptInformation ::= SEQUENCE {
pagingAttemptCount PagingAttemptCount,
intendedNumberOfPagingAttempts IntendedNumberOfPagingAttempts,
nextPagingAreaScope NextPagingAreaScope OPTIONAL,
iE-Extensions ProtocolExtensionContainer { {PagingAttemptInformation-ExtIEs} } OPTIONAL,
...
}
PagingAttemptInformation-ExtIEs NGAP-PROTOCOL-EXTENSION ::= {
...
}
PagingAttemptCount ::= INTEGER (1..16, ...)
PagingCause ::= ENUMERATED {
voice,
...
}
PagingCauseIndicationForVoiceService ::= ENUMERATED {
supported,
...
}
PagingDRX ::= ENUMERATED {
v32,
v64,
v128,
v256,
...
}
PagingOrigin ::= ENUMERATED {
non-3gpp,
...
}
PagingPolicyDifferentiation ::= SEQUENCE {
pDUSessionForPagingList PDUSessionForPagingList,
iE-Extensions ProtocolExtensionContainer { { PagingPolicyDifferentiation-ExtIEs} } OPTIONAL,
...
}
PagingPolicyDifferentiation-ExtIEs NGAP-PROTOCOL-EXTENSION ::= {
...
}
PDUSessionForPagingList ::= SEQUENCE (SIZE(1..maxnoofPDUSessions)) OF PDUSessionForPagingItem
PDUSessionForPagingItem ::= SEQUENCE {
pDUSessionID PDUSessionID,
pagingPolicyDifferentiationList PagingPolicyDifferentiationList,
iE-Extensions ProtocolExtensionContainer { { PDUSessionForPagingItem-ExtIEs} } OPTIONAL,
...
}
PDUSessionForPagingItem-ExtIEs NGAP-PROTOCOL-EXTENSION ::= {
...
}
PagingPolicyDifferentiationList ::= SEQUENCE (SIZE(1..maxnoofQosFlows)) OF PagingPolicyDifferentiationItem
PagingPolicyDifferentiationItem ::= SEQUENCE {
qosFlowIdentifier QosFlowIdentifier OPTIONAL,
pagingPolicyIndicator PagingPolicyIndicator OPTIONAL,
allocationAndRetentionPriority AllocationAndRetentionPriority OPTIONAL,
fiveQI FiveQI OPTIONAL,
dl-DataSize INTEGER (0..96000, ...) OPTIONAL,
iE-Extensions ProtocolExtensionContainer { { PagingPolicyDifferentiationItem-ExtIEs} } OPTIONAL,
...
}
PagingPolicyDifferentiationItem-ExtIEs NGAP-PROTOCOL-EXTENSION ::= {
...
}
PagingPolicyIndicator ::= INTEGER (0..7, ...)
PagingPriority ::= ENUMERATED {
priolevel1,
priolevel2,
priolevel3,
priolevel4,
priolevel5,
priolevel6,
priolevel7,
priolevel8,
...
}
PagingProbabilityInformation ::= ENUMERATED {
p00, p05, p10, p15, p20, p25, p30, p35, p40, p45, p50, p55, p60, p65, p70, p75, p80, p85, p90, p95, p100,
...
}
ParentTImeSource ::= ENUMERATED {synce, ptp, gnss, atomicclock, terrestrialradio, serialtimecode, ntp, handset, other, ...}
Partially-Allowed-NSSAI ::= SEQUENCE (SIZE(1.. maxnoofPartiallyAllowedS-NSSAIs)) OF PartiallyAllowedNSSAI-Item
PartiallyAllowedNSSAI-Item ::= SEQUENCE {
s-NSSAI S-NSSAI,
iE-Extensions ProtocolExtensionContainer { {PartiallyAllowedNSSAI-Item-ExtIEs} } OPTIONAL,
...
}
PartiallyAllowedNSSAI-Item-ExtIEs NGAP-PROTOCOL-EXTENSION ::= {
...
}
PathSwitchRequestAcknowledgeTransfer ::= SEQUENCE {
uL-NGU-UP-TNLInformation UPTransportLayerInformation OPTIONAL,
securityIndication SecurityIndication OPTIONAL,
iE-Extensions ProtocolExtensionContainer { {PathSwitchRequestAcknowledgeTransfer-ExtIEs} } OPTIONAL,
...
}
PathSwitchRequestAcknowledgeTransfer-ExtIEs NGAP-PROTOCOL-EXTENSION ::= {
{ ID id-AdditionalNGU-UP-TNLInformation CRITICALITY ignore EXTENSION UPTransportLayerInformationPairList PRESENCE optional }|
{ ID id-RedundantUL-NGU-UP-TNLInformation CRITICALITY ignore EXTENSION UPTransportLayerInformation PRESENCE optional }|
{ ID id-AdditionalRedundantNGU-UP-TNLInformation CRITICALITY ignore EXTENSION UPTransportLayerInformationPairList PRESENCE optional }|
{ ID id-QosFlowParametersList CRITICALITY ignore EXTENSION QosFlowParametersList PRESENCE optional },
...
}
PathSwitchRequestSetupFailedTransfer ::= SEQUENCE {
cause Cause,
iE-Extensions ProtocolExtensionContainer { {PathSwitchRequestSetupFailedTransfer-ExtIEs} } OPTIONAL,
...
}
PathSwitchRequestSetupFailedTransfer-ExtIEs NGAP-PROTOCOL-EXTENSION ::= {
...
}
PathSwitchRequestTransfer ::= SEQUENCE {
dL-NGU-UP-TNLInformation UPTransportLayerInformation,
dL-NGU-TNLInformationReused DL-NGU-TNLInformationReused OPTIONAL,
userPlaneSecurityInformation UserPlaneSecurityInformation OPTIONAL,
qosFlowAcceptedList QosFlowAcceptedList,
iE-Extensions ProtocolExtensionContainer { {PathSwitchRequestTransfer-ExtIEs} } OPTIONAL,
...
}
PathSwitchRequestTransfer-ExtIEs NGAP-PROTOCOL-EXTENSION ::= {
{ ID id-AdditionalDLQosFlowPerTNLInformation CRITICALITY ignore EXTENSION QosFlowPerTNLInformationList PRESENCE optional }|
{ ID id-RedundantDL-NGU-UP-TNLInformation CRITICALITY ignore EXTENSION UPTransportLayerInformation PRESENCE optional }|
{ ID id-RedundantDL-NGU-TNLInformationReused CRITICALITY ignore EXTENSION DL-NGU-TNLInformationReused PRESENCE optional }|
{ ID id-AdditionalRedundantDLQosFlowPerTNLInformation CRITICALITY ignore EXTENSION QosFlowPerTNLInformationList PRESENCE optional }|
{ ID id-UsedRSNInformation CRITICALITY ignore EXTENSION RedundantPDUSessionInformation PRESENCE optional }|
{ ID id-GlobalRANNodeID CRITICALITY ignore EXTENSION GlobalRANNodeID PRESENCE optional }|
{ ID id-MBS-SupportIndicator CRITICALITY ignore EXTENSION MBS-SupportIndicator PRESENCE optional }|
{ ID id-PDUSetbasedHandlingIndicator CRITICALITY ignore EXTENSION PDUSetbasedHandlingIndicator PRESENCE optional }|
{ ID id-ECNMarkingorCongestionInformationReportingStatus CRITICALITY ignore EXTENSION ECNMarkingorCongestionInformationReportingStatus PRESENCE optional },
...
}
PathSwitchRequestUnsuccessfulTransfer ::= SEQUENCE {
cause Cause,
iE-Extensions ProtocolExtensionContainer { {PathSwitchRequestUnsuccessfulTransfer-ExtIEs} } OPTIONAL,
...
}
PathSwitchRequestUnsuccessfulTransfer-ExtIEs NGAP-PROTOCOL-EXTENSION ::= {
...
}
PC5QoSParameters ::= SEQUENCE {
pc5QoSFlowList PC5QoSFlowList,
pc5LinkAggregateBitRates BitRate OPTIONAL,
iE-Extensions ProtocolExtensionContainer { { PC5QoSParameters-ExtIEs} } OPTIONAL,
...
}
PC5QoSParameters-ExtIEs NGAP-PROTOCOL-EXTENSION ::= {
...
}
PC5QoSFlowList ::= SEQUENCE (SIZE(1..maxnoofPC5QoSFlows)) OF PC5QoSFlowItem
PC5QoSFlowItem::= SEQUENCE {
pQI FiveQI,
pc5FlowBitRates PC5FlowBitRates OPTIONAL,
range Range OPTIONAL,
iE-Extensions ProtocolExtensionContainer { { PC5QoSFlowItem-ExtIEs} } OPTIONAL,
...
}
PC5QoSFlowItem-ExtIEs NGAP-PROTOCOL-EXTENSION ::= {
...
}
PC5FlowBitRates ::= SEQUENCE {
guaranteedFlowBitRate BitRate,
maximumFlowBitRate BitRate,
iE-Extensions ProtocolExtensionContainer { { PC5FlowBitRates-ExtIEs} } OPTIONAL,
...
}
PC5FlowBitRates-ExtIEs NGAP-PROTOCOL-EXTENSION ::= {
...
}
PCIListForMDT ::= SEQUENCE (SIZE(1.. maxnoofNeighPCIforMDT)) OF NR-PCI
PrivacyIndicator ::= ENUMERATED {
immediate-MDT,
logged-MDT,
...
}
PDUSessionAggregateMaximumBitRate ::= SEQUENCE {
pDUSessionAggregateMaximumBitRateDL BitRate,
pDUSessionAggregateMaximumBitRateUL BitRate,
iE-Extensions ProtocolExtensionContainer { {PDUSessionAggregateMaximumBitRate-ExtIEs} } OPTIONAL,
...
}
PDUSessionAggregateMaximumBitRate-ExtIEs NGAP-PROTOCOL-EXTENSION ::= {
...
}
PDUSessionID ::= INTEGER (0..255)
PDUSessionPairID ::= INTEGER (0..255, ...)
PDUSessionResourceAdmittedList ::= SEQUENCE (SIZE(1..maxnoofPDUSessions)) OF PDUSessionResourceAdmittedItem
PDUSessionResourceAdmittedItem ::= SEQUENCE {
pDUSessionID PDUSessionID,
handoverRequestAcknowledgeTransfer OCTET STRING (CONTAINING HandoverRequestAcknowledgeTransfer),
iE-Extensions ProtocolExtensionContainer { {PDUSessionResourceAdmittedItem-ExtIEs} } OPTIONAL,
...
}
PDUSessionResourceAdmittedItem-ExtIEs NGAP-PROTOCOL-EXTENSION ::= {
...
}
PDUSessionResourceFailedToModifyListModCfm ::= SEQUENCE (SIZE(1..maxnoofPDUSessions)) OF PDUSessionResourceFailedToModifyItemModCfm
PDUSessionResourceFailedToModifyItemModCfm ::= SEQUENCE {
pDUSessionID PDUSessionID,
pDUSessionResourceModifyIndicationUnsuccessfulTransfer OCTET STRING (CONTAINING PDUSessionResourceModifyIndicationUnsuccessfulTransfer),
iE-Extensions ProtocolExtensionContainer { {PDUSessionResourceFailedToModifyItemModCfm-ExtIEs} } OPTIONAL,
...
}
PDUSessionResourceFailedToModifyItemModCfm-ExtIEs NGAP-PROTOCOL-EXTENSION ::= {
...
}
PDUSessionResourceFailedToModifyListModRes ::= SEQUENCE (SIZE(1..maxnoofPDUSessions)) OF PDUSessionResourceFailedToModifyItemModRes
PDUSessionResourceFailedToModifyItemModRes ::= SEQUENCE {
pDUSessionID PDUSessionID,
pDUSessionResourceModifyUnsuccessfulTransfer OCTET STRING (CONTAINING PDUSessionResourceModifyUnsuccessfulTransfer),
iE-Extensions ProtocolExtensionContainer { {PDUSessionResourceFailedToModifyItemModRes-ExtIEs} } OPTIONAL,
...
}
PDUSessionResourceFailedToModifyItemModRes-ExtIEs NGAP-PROTOCOL-EXTENSION ::= {
...
}
PDUSessionResourceFailedToResumeListRESReq ::= SEQUENCE (SIZE(1..maxnoofPDUSessions)) OF PDUSessionResourceFailedToResumeItemRESReq
PDUSessionResourceFailedToResumeItemRESReq ::= SEQUENCE {
pDUSessionID PDUSessionID,
cause Cause,
iE-Extensions ProtocolExtensionContainer { {PDUSessionResourceFailedToResumeItemRESReq-ExtIEs} } OPTIONAL,
...
}
PDUSessionResourceFailedToResumeItemRESReq-ExtIEs NGAP-PROTOCOL-EXTENSION ::= {
...
}
PDUSessionResourceFailedToResumeListRESRes ::= SEQUENCE (SIZE(1..maxnoofPDUSessions)) OF PDUSessionResourceFailedToResumeItemRESRes
PDUSessionResourceFailedToResumeItemRESRes ::= SEQUENCE {
pDUSessionID PDUSessionID,
cause Cause,
iE-Extensions ProtocolExtensionContainer { {PDUSessionResourceFailedToResumeItemRESRes-ExtIEs} } OPTIONAL,
...
}
PDUSessionResourceFailedToResumeItemRESRes-ExtIEs NGAP-PROTOCOL-EXTENSION ::= {
...
}
PDUSessionResourceFailedToSetupListCxtFail ::= SEQUENCE (SIZE(1..maxnoofPDUSessions)) OF PDUSessionResourceFailedToSetupItemCxtFail
PDUSessionResourceFailedToSetupItemCxtFail ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemCxtFail-ExtIEs} } OPTIONAL,
...
}
PDUSessionResourceFailedToSetupItemCxtFail-ExtIEs NGAP-PROTOCOL-EXTENSION ::= {
...
}
PDUSessionResourceFailedToSetupListCxtRes ::= SEQUENCE (SIZE(1..maxnoofPDUSessions)) OF PDUSessionResourceFailedToSetupItemCxtRes
PDUSessionResourceFailedToSetupItemCxtRes ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemCxtRes-ExtIEs} } OPTIONAL,
...
}
PDUSessionResourceFailedToSetupItemCxtRes-ExtIEs NGAP-PROTOCOL-EXTENSION ::= {
...
}
PDUSessionResourceFailedToSetupListHOAck ::= SEQUENCE (SIZE(1..maxnoofPDUSessions)) OF PDUSessionResourceFailedToSetupItemHOAck
PDUSessionResourceFailedToSetupItemHOAck ::= SEQUENCE {
pDUSessionID PDUSessionID,
handoverResourceAllocationUnsuccessfulTransfer OCTET STRING (CONTAINING HandoverResourceAllocationUnsuccessfulTransfer),
iE-Extensions ProtocolExtensionContainer { {PDUSessionResourceFailedToSetupItemHOAck-ExtIEs} } OPTIONAL,
...
}
PDUSessionResourceFailedToSetupItemHOAck-ExtIEs NGAP-PROTOCOL-EXTENSION ::= {
...
}
PDUSessionResourceFailedToSetupListPSReq ::= SEQUENCE (SIZE(1..maxnoofPDUSessions)) OF PDUSessionResourceFailedToSetupItemPSReq
PDUSessionResourceFailedToSetupItemPSReq ::= SEQUENCE {
pDUSessionID PDUSessionID,
pathSwitchRequestSetupFailedTransfer OCTET STRING (CONTAINING PathSwitchRequestSetupFailedTransfer),
iE-Extensions ProtocolExtensionContainer { {PDUSessionResourceFailedToSetupItemPSReq-ExtIEs} } OPTIONAL,
...
}
PDUSessionResourceFailedToSetupItemPSReq-ExtIEs NGAP-PROTOCOL-EXTENSION ::= {
...
}
PDUSessionResourceFailedToSetupListSURes ::= SEQUENCE (SIZE(1..maxnoofPDUSessions)) OF PDUSessionResourceFailedToSetupItemSURes
PDUSessionResourceFailedToSetupItemSURes ::= SEQUENCE {
pDUSessionID PDUSessionID,
pDUSessionResourceSetupUnsuccessfulTransfer OCTET STRING (CONTAINING PDUSessionResourceSetupUnsuccessfulTransfer),
iE-Extensions ProtocolExtensionContainer { {PDUSessionResourceFailedToSetupItemSURes-ExtIEs} } OPTIONAL,
...
}
PDUSessionResourceFailedToSetupItemSURes-ExtIEs NGAP-PROTOCOL-EXTENSION ::= {
...
}
PDUSessionResourceHandoverList ::= SEQUENCE (SIZE(1..maxnoofPDUSessions)) OF PDUSessionResourceHandoverItem
PDUSessionResourceHandoverItem ::= SEQUENCE {
pDUSessionID PDUSessionID,
handoverCommandTransfer OCTET STRING (CONTAINING HandoverCommandTransfer),
iE-Extensions ProtocolExtensionContainer { {PDUSessionResourceHandoverItem-ExtIEs} } OPTIONAL,
...
}
PDUSessionResourceHandoverItem-ExtIEs NGAP-PROTOCOL-EXTENSION ::= {
...
}
PDUSessionResourceInformationList ::= SEQUENCE (SIZE(1..maxnoofPDUSessions)) OF PDUSessionResourceInformationItem
PDUSessionResourceInformationItem ::= SEQUENCE {
pDUSessionID PDUSessionID,
qosFlowInformationList QosFlowInformationList,
dRBsToQosFlowsMappingList DRBsToQosFlowsMappingList OPTIONAL,
iE-Extensions ProtocolExtensionContainer { {PDUSessionResourceInformationItem-ExtIEs} } OPTIONAL,
...
}
PDUSessionResourceInformationItem-ExtIEs NGAP-PROTOCOL-EXTENSION ::= {
...
}
PDUSessionResourceListCxtRelCpl ::= SEQUENCE (SIZE(1..maxnoofPDUSessions)) OF PDUSessionResourceItemCxtRelCpl
PDUSessionResourceItemCxtRelCpl ::= SEQUENCE {
pDUSessionID PDUSessionID,
iE-Extensions ProtocolExtensionContainer { {PDUSessionResourceItemCxtRelCpl-ExtIEs} } OPTIONAL,
...
}
PDUSessionResourceItemCxtRelCpl-ExtIEs NGAP-PROTOCOL-EXTENSION ::= {
{ ID id-PDUSessionResourceReleaseResponseTransfer CRITICALITY ignore EXTENSION OCTET STRING (CONTAINING PDUSessionResourceReleaseResponseTransfer) PRESENCE optional },
...
}
PDUSessionResourceListCxtRelReq ::= SEQUENCE (SIZE(1..maxnoofPDUSessions)) OF PDUSessionResourceItemCxtRelReq
PDUSessionResourceItemCxtRelReq ::= SEQUENCE {
pDUSessionID PDUSessionID,
iE-Extensions ProtocolExtensionContainer { {PDUSessionResourceItemCxtRelReq-ExtIEs} } OPTIONAL,
...
}
PDUSessionResourceItemCxtRelReq-ExtIEs NGAP-PROTOCOL-EXTENSION ::= {
...
}
PDUSessionResourceListHORqd ::= SEQUENCE (SIZE(1..maxnoofPDUSessions)) OF PDUSessionResourceItemHORqd
PDUSessionResourceItemHORqd ::= SEQUENCE {
pDUSessionID PDUSessionID,
handoverRequiredTransfer OCTET STRING (CONTAINING HandoverRequiredTransfer),
iE-Extensions ProtocolExtensionContainer { {PDUSessionResourceItemHORqd-ExtIEs} } OPTIONAL,
...
}
PDUSessionResourceItemHORqd-ExtIEs NGAP-PROTOCOL-EXTENSION ::= {
...
}
PDUSessionListMTCommHReq ::= SEQUENCE (SIZE(1..maxnoofPDUSessions)) OF PDUSessionListMTCommHReq-Item
PDUSessionListMTCommHReq-Item ::= SEQUENCE {
pDUSessionID PDUSessionID,
iE-Extensions ProtocolExtensionContainer { { PDUSessionListMTCommHReq-Item-ExtIEs} } OPTIONAL,
...
}
PDUSessionListMTCommHReq-Item-ExtIEs NGAP-PROTOCOL-EXTENSION ::= {
...
}
PDUSessionResourceModifyConfirmTransfer ::= SEQUENCE {
qosFlowModifyConfirmList QosFlowModifyConfirmList,
uLNGU-UP-TNLInformation UPTransportLayerInformation,
additionalNG-UUPTNLInformation UPTransportLayerInformationPairList OPTIONAL,
qosFlowFailedToModifyList QosFlowListWithCause OPTIONAL,
iE-Extensions ProtocolExtensionContainer { {PDUSessionResourceModifyConfirmTransfer-ExtIEs} } OPTIONAL,
...
}
PDUSessionResourceModifyConfirmTransfer-ExtIEs NGAP-PROTOCOL-EXTENSION ::= {
{ ID id-RedundantUL-NGU-UP-TNLInformation CRITICALITY ignore EXTENSION UPTransportLayerInformation PRESENCE optional }|
{ ID id-AdditionalRedundantNGU-UP-TNLInformation CRITICALITY ignore EXTENSION UPTransportLayerInformationPairList PRESENCE optional },
...
}
PDUSessionResourceModifyIndicationUnsuccessfulTransfer ::= SEQUENCE {
cause Cause,
iE-Extensions ProtocolExtensionContainer { {PDUSessionResourceModifyIndicationUnsuccessfulTransfer-ExtIEs} } OPTIONAL,
...
}
PDUSessionResourceModifyIndicationUnsuccessfulTransfer-ExtIEs NGAP-PROTOCOL-EXTENSION ::= {
...
}
PDUSessionResourceModifyRequestTransfer ::= SEQUENCE {
protocolIEs ProtocolIE-Container { {PDUSessionResourceModifyRequestTransferIEs} },
...
}
PDUSessionResourceModifyRequestTransferIEs NGAP-PROTOCOL-IES ::= {
{ ID id-PDUSessionAggregateMaximumBitRate CRITICALITY reject TYPE PDUSessionAggregateMaximumBitRate PRESENCE optional }|
{ ID id-UL-NGU-UP-TNLModifyList CRITICALITY reject TYPE UL-NGU-UP-TNLModifyList PRESENCE optional }|
{ ID id-NetworkInstance CRITICALITY reject TYPE NetworkInstance PRESENCE optional }|
{ ID id-QosFlowAddOrModifyRequestList CRITICALITY reject TYPE QosFlowAddOrModifyRequestList PRESENCE optional }|
{ ID id-QosFlowToReleaseList CRITICALITY reject TYPE QosFlowListWithCause PRESENCE optional }|
{ ID id-AdditionalUL-NGU-UP-TNLInformation CRITICALITY reject TYPE UPTransportLayerInformationList PRESENCE optional }|
{ ID id-CommonNetworkInstance CRITICALITY ignore TYPE CommonNetworkInstance PRESENCE optional }|
{ ID id-AdditionalRedundantUL-NGU-UP-TNLInformation CRITICALITY ignore TYPE UPTransportLayerInformationList PRESENCE optional }|
{ ID id-RedundantCommonNetworkInstance CRITICALITY ignore TYPE CommonNetworkInstance PRESENCE optional }|
{ ID id-RedundantUL-NGU-UP-TNLInformation CRITICALITY ignore TYPE UPTransportLayerInformation PRESENCE optional }|
{ ID id-SecurityIndication CRITICALITY ignore TYPE SecurityIndication PRESENCE optional }|
{ ID id-MBSSessionSetuporModifyRequestList CRITICALITY ignore TYPE MBSSessionSetuporModifyRequestList PRESENCE optional }|
{ ID id-MBSSessionToReleaseList CRITICALITY ignore TYPE MBSSessionToReleaseList PRESENCE optional }|
{ ID id-UserPlaneFailureIndication CRITICALITY ignore TYPE UserPlaneFailureIndication PRESENCE optional },
...
}
PDUSessionResourceModifyResponseTransfer ::= SEQUENCE {
dL-NGU-UP-TNLInformation UPTransportLayerInformation OPTIONAL,
uL-NGU-UP-TNLInformation UPTransportLayerInformation OPTIONAL,
qosFlowAddOrModifyResponseList QosFlowAddOrModifyResponseList OPTIONAL,
additionalDLQosFlowPerTNLInformation QosFlowPerTNLInformationList OPTIONAL,
qosFlowFailedToAddOrModifyList QosFlowListWithCause OPTIONAL,
iE-Extensions ProtocolExtensionContainer { {PDUSessionResourceModifyResponseTransfer-ExtIEs} } OPTIONAL,
...
}
PDUSessionResourceModifyResponseTransfer-ExtIEs NGAP-PROTOCOL-EXTENSION ::= {
{ ID id-AdditionalNGU-UP-TNLInformation CRITICALITY ignore EXTENSION UPTransportLayerInformationPairList PRESENCE optional }|
{ ID id-RedundantDL-NGU-UP-TNLInformation CRITICALITY ignore EXTENSION UPTransportLayerInformation PRESENCE optional }|
{ ID id-RedundantUL-NGU-UP-TNLInformation CRITICALITY ignore EXTENSION UPTransportLayerInformation PRESENCE optional }|
{ ID id-AdditionalRedundantDLQosFlowPerTNLInformation CRITICALITY ignore EXTENSION QosFlowPerTNLInformationList PRESENCE optional }|
{ ID id-AdditionalRedundantNGU-UP-TNLInformation CRITICALITY ignore EXTENSION UPTransportLayerInformationPairList PRESENCE optional }|
{ ID id-SecondaryRATUsageInformation CRITICALITY ignore EXTENSION SecondaryRATUsageInformation PRESENCE optional }|
{ ID id-MBS-SupportIndicator CRITICALITY ignore EXTENSION MBS-SupportIndicator PRESENCE optional }|
{ ID id-MBSSessionSetuporModifyResponseList CRITICALITY ignore EXTENSION MBSSessionSetupResponseList PRESENCE optional }|
{ ID id-MBSSessionFailedtoSetuporModifyList CRITICALITY ignore EXTENSION MBSSessionFailedtoSetupList PRESENCE optional }|
{ ID id-ECNMarkingorCongestionInformationReportingStatus CRITICALITY ignore EXTENSION ECNMarkingorCongestionInformationReportingStatus PRESENCE optional }|
{ ID id-PDUSetbasedHandlingIndicator CRITICALITY ignore EXTENSION PDUSetbasedHandlingIndicator PRESENCE optional }|
{ ID id-UserPlaneFailureIndicationReport CRITICALITY ignore EXTENSION UserPlaneFailureIndicationReport PRESENCE optional },
...
}
PDUSessionResourceModifyIndicationTransfer ::= SEQUENCE {
dLQosFlowPerTNLInformation QosFlowPerTNLInformation,
additionalDLQosFlowPerTNLInformation QosFlowPerTNLInformationList OPTIONAL,
iE-Extensions ProtocolExtensionContainer { {PDUSessionResourceModifyIndicationTransfer-ExtIEs} } OPTIONAL,
...
}
PDUSessionResourceModifyIndicationTransfer-ExtIEs NGAP-PROTOCOL-EXTENSION ::= {
{ ID id-SecondaryRATUsageInformation CRITICALITY ignore EXTENSION SecondaryRATUsageInformation PRESENCE optional }|
{ ID id-SecurityResult CRITICALITY ignore EXTENSION SecurityResult PRESENCE optional }|
{ ID id-RedundantDLQosFlowPerTNLInformation CRITICALITY ignore EXTENSION QosFlowPerTNLInformation PRESENCE optional }|
{ ID id-AdditionalRedundantDLQosFlowPerTNLInformation CRITICALITY ignore EXTENSION QosFlowPerTNLInformationList PRESENCE optional }|
{ ID id-GlobalRANNodeID CRITICALITY ignore EXTENSION GlobalRANNodeID PRESENCE optional }|
{ ID id-ECNMarkingorCongestionInformationReportingStatus CRITICALITY ignore EXTENSION ECNMarkingorCongestionInformationReportingStatus PRESENCE optional },
...
}
PDUSessionResourceModifyListModCfm ::= SEQUENCE (SIZE(1..maxnoofPDUSessions)) OF PDUSessionResourceModifyItemModCfm
PDUSessionResourceModifyItemModCfm ::= SEQUENCE {
pDUSessionID PDUSessionID,
pDUSessionResourceModifyConfirmTransfer OCTET STRING (CONTAINING PDUSessionResourceModifyConfirmTransfer),
iE-Extensions ProtocolExtensionContainer { {PDUSessionResourceModifyItemModCfm-ExtIEs} } OPTIONAL,
...
}
PDUSessionResourceModifyItemModCfm-ExtIEs NGAP-PROTOCOL-EXTENSION ::= {
...
}
PDUSessionResourceModifyListModInd ::= SEQUENCE (SIZE(1..maxnoofPDUSessions)) OF PDUSessionResourceModifyItemModInd
PDUSessionResourceModifyItemModInd ::= SEQUENCE {
pDUSessionID PDUSessionID,
pDUSessionResourceModifyIndicationTransfer OCTET STRING (CONTAINING PDUSessionResourceModifyIndicationTransfer),
iE-Extensions ProtocolExtensionContainer { {PDUSessionResourceModifyItemModInd-ExtIEs} } OPTIONAL,
...
}
PDUSessionResourceModifyItemModInd-ExtIEs NGAP-PROTOCOL-EXTENSION ::= {
...
}
PDUSessionResourceModifyListModReq ::= SEQUENCE (SIZE(1..maxnoofPDUSessions)) OF PDUSessionResourceModifyItemModReq
PDUSessionResourceModifyItemModReq ::= SEQUENCE {
pDUSessionID PDUSessionID,
nAS-PDU NAS-PDU OPTIONAL,
pDUSessionResourceModifyRequestTransfer OCTET STRING (CONTAINING PDUSessionResourceModifyRequestTransfer),
iE-Extensions ProtocolExtensionContainer { {PDUSessionResourceModifyItemModReq-ExtIEs} } OPTIONAL,
...
}
PDUSessionResourceModifyItemModReq-ExtIEs NGAP-PROTOCOL-EXTENSION ::= {
{ ID id-S-NSSAI CRITICALITY reject EXTENSION S-NSSAI PRESENCE optional }|
{ ID id-PduSessionExpectedUEActivityBehaviour CRITICALITY ignore EXTENSION ExpectedUEActivityBehaviour PRESENCE optional },
...
}
PDUSessionResourceModifyListModRes ::= SEQUENCE (SIZE(1..maxnoofPDUSessions)) OF PDUSessionResourceModifyItemModRes
PDUSessionResourceModifyItemModRes ::= SEQUENCE {
pDUSessionID PDUSessionID,
pDUSessionResourceModifyResponseTransfer OCTET STRING (CONTAINING PDUSessionResourceModifyResponseTransfer),
iE-Extensions ProtocolExtensionContainer { {PDUSessionResourceModifyItemModRes-ExtIEs} } OPTIONAL,
...
}
PDUSessionResourceModifyItemModRes-ExtIEs NGAP-PROTOCOL-EXTENSION ::= {
...
}
PDUSessionResourceModifyUnsuccessfulTransfer ::= SEQUENCE {
cause Cause,
criticalityDiagnostics CriticalityDiagnostics OPTIONAL,
iE-Extensions ProtocolExtensionContainer { {PDUSessionResourceModifyUnsuccessfulTransfer-ExtIEs} } OPTIONAL,
...
}
PDUSessionResourceModifyUnsuccessfulTransfer-ExtIEs NGAP-PROTOCOL-EXTENSION ::= {
...
}
PDUSessionResourceNotifyList ::= SEQUENCE (SIZE(1..maxnoofPDUSessions)) OF PDUSessionResourceNotifyItem
PDUSessionResourceNotifyItem ::= SEQUENCE {
pDUSessionID PDUSessionID,
pDUSessionResourceNotifyTransfer OCTET STRING (CONTAINING PDUSessionResourceNotifyTransfer),
iE-Extensions ProtocolExtensionContainer { {PDUSessionResourceNotifyItem-ExtIEs} } OPTIONAL,
...
}
PDUSessionResourceNotifyItem-ExtIEs NGAP-PROTOCOL-EXTENSION ::= {
...
}
PDUSessionResourceNotifyReleasedTransfer ::= SEQUENCE {
cause Cause,
iE-Extensions ProtocolExtensionContainer { {PDUSessionResourceNotifyReleasedTransfer-ExtIEs} } OPTIONAL,
...
}
PDUSessionResourceNotifyReleasedTransfer-ExtIEs NGAP-PROTOCOL-EXTENSION ::= {
{ ID id-SecondaryRATUsageInformation CRITICALITY ignore EXTENSION SecondaryRATUsageInformation PRESENCE optional }|
{ ID id-UserPlaneErrorIndicator CRITICALITY ignore EXTENSION UserPlaneErrorIndicator PRESENCE optional },
...
}
UserPlaneErrorIndicator ::= ENUMERATED {
gTP-U-error-indication-received,
...
}
PDUSessionResourceNotifyTransfer ::= SEQUENCE {
qosFlowNotifyList QosFlowNotifyList OPTIONAL,
qosFlowReleasedList QosFlowListWithCause OPTIONAL,
iE-Extensions ProtocolExtensionContainer { {PDUSessionResourceNotifyTransfer-ExtIEs} } OPTIONAL,
...
}
PDUSessionResourceNotifyTransfer-ExtIEs NGAP-PROTOCOL-EXTENSION ::= {
{ ID id-SecondaryRATUsageInformation CRITICALITY ignore EXTENSION SecondaryRATUsageInformation PRESENCE optional }|
{ ID id-QosFlowFeedbackList CRITICALITY ignore EXTENSION QosFlowFeedbackList PRESENCE optional },
...
}
PDUSessionResourceReleaseCommandTransfer ::= SEQUENCE {
cause Cause,
iE-Extensions ProtocolExtensionContainer { {PDUSessionResourceReleaseCommandTransfer-ExtIEs} } OPTIONAL,
...
}
PDUSessionResourceReleaseCommandTransfer-ExtIEs NGAP-PROTOCOL-EXTENSION ::= {
{ ID id-QosFlowAdditionalInfoList CRITICALITY ignore EXTENSION QosFlowAdditionalInfoListRelCom PRESENCE optional },
...
}
PDUSessionResourceReleasedListNot ::= SEQUENCE (SIZE(1..maxnoofPDUSessions)) OF PDUSessionResourceReleasedItemNot
PDUSessionResourceReleasedItemNot ::= SEQUENCE {
pDUSessionID PDUSessionID,
pDUSessionResourceNotifyReleasedTransfer OCTET STRING (CONTAINING PDUSessionResourceNotifyReleasedTransfer),
iE-Extensions ProtocolExtensionContainer { {PDUSessionResourceReleasedItemNot-ExtIEs} } OPTIONAL,
...
}
PDUSessionResourceReleasedItemNot-ExtIEs NGAP-PROTOCOL-EXTENSION ::= {
...
}
PDUSessionResourceReleasedListPSAck ::= SEQUENCE (SIZE(1..maxnoofPDUSessions)) OF PDUSessionResourceReleasedItemPSAck
PDUSessionResourceReleasedItemPSAck ::= SEQUENCE {
pDUSessionID PDUSessionID,
pathSwitchRequestUnsuccessfulTransfer OCTET STRING (CONTAINING PathSwitchRequestUnsuccessfulTransfer),
iE-Extensions ProtocolExtensionContainer { {PDUSessionResourceReleasedItemPSAck-ExtIEs} } OPTIONAL,
...
}
PDUSessionResourceReleasedItemPSAck-ExtIEs NGAP-PROTOCOL-EXTENSION ::= {
...
}
PDUSessionResourceReleasedListPSFail ::= SEQUENCE (SIZE(1..maxnoofPDUSessions)) OF PDUSessionResourceReleasedItemPSFail
PDUSessionResourceReleasedItemPSFail ::= SEQUENCE {
pDUSessionID PDUSessionID,
pathSwitchRequestUnsuccessfulTransfer OCTET STRING (CONTAINING PathSwitchRequestUnsuccessfulTransfer),
iE-Extensions ProtocolExtensionContainer { {PDUSessionResourceReleasedItemPSFail-ExtIEs} } OPTIONAL,
...
}
PDUSessionResourceReleasedItemPSFail-ExtIEs NGAP-PROTOCOL-EXTENSION ::= {
...
}
PDUSessionResourceReleasedListRelRes ::= SEQUENCE (SIZE(1..maxnoofPDUSessions)) OF PDUSessionResourceReleasedItemRelRes
PDUSessionResourceReleasedItemRelRes ::= SEQUENCE {
pDUSessionID PDUSessionID,
pDUSessionResourceReleaseResponseTransfer OCTET STRING (CONTAINING PDUSessionResourceReleaseResponseTransfer),
iE-Extensions ProtocolExtensionContainer { {PDUSessionResourceReleasedItemRelRes-ExtIEs} } OPTIONAL,
...
}
PDUSessionResourceReleasedItemRelRes-ExtIEs NGAP-PROTOCOL-EXTENSION ::= {
...
}
PDUSessionResourceReleaseResponseTransfer ::= SEQUENCE {
iE-Extensions ProtocolExtensionContainer { {PDUSessionResourceReleaseResponseTransfer-ExtIEs} } OPTIONAL,
...
}
PDUSessionResourceReleaseResponseTransfer-ExtIEs NGAP-PROTOCOL-EXTENSION ::= {
{ ID id-SecondaryRATUsageInformation CRITICALITY ignore EXTENSION SecondaryRATUsageInformation PRESENCE optional }|
{ ID id-QosFlowAdditionalInfoList CRITICALITY ignore EXTENSION QosFlowAdditionalInfoListRelRes PRESENCE optional },
...
}
PDUSessionResourceResumeListRESReq ::= SEQUENCE (SIZE(1..maxnoofPDUSessions)) OF PDUSessionResourceResumeItemRESReq
PDUSessionResourceResumeItemRESReq ::= SEQUENCE {
pDUSessionID PDUSessionID,
uEContextResumeRequestTransfer OCTET STRING (CONTAINING UEContextResumeRequestTransfer),
iE-Extensions ProtocolExtensionContainer { {PDUSessionResourceResumeItemRESReq-ExtIEs} } OPTIONAL,
...
}
PDUSessionResourceResumeItemRESReq-ExtIEs NGAP-PROTOCOL-EXTENSION ::= {
...
}
PDUSessionResourceResumeListRESRes ::= SEQUENCE (SIZE(1..maxnoofPDUSessions)) OF PDUSessionResourceResumeItemRESRes
PDUSessionResourceResumeItemRESRes ::= SEQUENCE {
pDUSessionID PDUSessionID,
uEContextResumeResponseTransfer OCTET STRING (CONTAINING UEContextResumeResponseTransfer),
iE-Extensions ProtocolExtensionContainer { {PDUSessionResourceResumeItemRESRes-ExtIEs} } OPTIONAL,
...
}
PDUSessionResourceResumeItemRESRes-ExtIEs NGAP-PROTOCOL-EXTENSION ::= {
...
}
PDUSessionResourceSecondaryRATUsageList ::= SEQUENCE (SIZE(1..maxnoofPDUSessions)) OF PDUSessionResourceSecondaryRATUsageItem
PDUSessionResourceSecondaryRATUsageItem ::= SEQUENCE {
pDUSessionID PDUSessionID,
secondaryRATDataUsageReportTransfer OCTET STRING (CONTAINING SecondaryRATDataUsageReportTransfer),
iE-Extensions ProtocolExtensionContainer { {PDUSessionResourceSecondaryRATUsageItem-ExtIEs} } OPTIONAL,
...
}
PDUSessionResourceSecondaryRATUsageItem-ExtIEs NGAP-PROTOCOL-EXTENSION ::= {
...
}
PDUSessionResourceSetupListCxtReq ::= SEQUENCE (SIZE(1..maxnoofPDUSessions)) OF PDUSessionResourceSetupItemCxtReq
PDUSessionResourceSetupItemCxtReq ::= SEQUENCE {
pDUSessionID PDUSessionID,
nAS-PDU NAS-PDU OPTIONAL,
s-NSSAI S-NSSAI,
pDUSessionResourceSetupRequestTransfer OCTET STRING (CONTAINING PDUSessionResourceSetupRequestTransfer),
iE-Extensions ProtocolExtensionContainer { {PDUSessionResourceSetupItemCxtReq-ExtIEs} } OPTIONAL,
...
}
PDUSessionResourceSetupItemCxtReq-ExtIEs NGAP-PROTOCOL-EXTENSION ::= {
{ ID id-PduSessionExpectedUEActivityBehaviour CRITICALITY ignore EXTENSION ExpectedUEActivityBehaviour PRESENCE optional },
...
}
PDUSessionResourceSetupListCxtRes ::= SEQUENCE (SIZE(1..maxnoofPDUSessions)) OF PDUSessionResourceSetupItemCxtRes
PDUSessionResourceSetupItemCxtRes ::= SEQUENCE {
pDUSessionID PDUSessionID,
pDUSessionResourceSetupResponseTransfer OCTET STRING (CONTAINING PDUSessionResourceSetupResponseTransfer),
iE-Extensions ProtocolExtensionContainer { {PDUSessionResourceSetupItemCxtRes-ExtIEs} } OPTIONAL,
...
}
PDUSessionResourceSetupItemCxtRes-ExtIEs NGAP-PROTOCOL-EXTENSION ::= {
...
}
PDUSessionResourceSetupListHOReq ::= SEQUENCE (SIZE(1..maxnoofPDUSessions)) OF PDUSessionResourceSetupItemHOReq
PDUSessionResourceSetupItemHOReq ::= SEQUENCE {
pDUSessionID PDUSessionID,
s-NSSAI S-NSSAI,
handoverRequestTransfer OCTET STRING (CONTAINING PDUSessionResourceSetupRequestTransfer),
iE-Extensions ProtocolExtensionContainer { {PDUSessionResourceSetupItemHOReq-ExtIEs} } OPTIONAL,
...
}
PDUSessionResourceSetupItemHOReq-ExtIEs NGAP-PROTOCOL-EXTENSION ::= {
{ ID id-PduSessionExpectedUEActivityBehaviour CRITICALITY ignore EXTENSION ExpectedUEActivityBehaviour PRESENCE optional },
...
}
PDUSessionResourceSetupListSUReq ::= SEQUENCE (SIZE(1..maxnoofPDUSessions)) OF PDUSessionResourceSetupItemSUReq
PDUSessionResourceSetupItemSUReq ::= SEQUENCE {
pDUSessionID PDUSessionID,
pDUSessionNAS-PDU NAS-PDU OPTIONAL,
s-NSSAI S-NSSAI,
pDUSessionResourceSetupRequestTransfer OCTET STRING (CONTAINING PDUSessionResourceSetupRequestTransfer),
iE-Extensions ProtocolExtensionContainer { {PDUSessionResourceSetupItemSUReq-ExtIEs} } OPTIONAL,
...
}
PDUSessionResourceSetupItemSUReq-ExtIEs NGAP-PROTOCOL-EXTENSION ::= {
{ ID id-PduSessionExpectedUEActivityBehaviour CRITICALITY ignore EXTENSION ExpectedUEActivityBehaviour PRESENCE optional },
...
}
PDUSessionResourceSetupListSURes ::= SEQUENCE (SIZE(1..maxnoofPDUSessions)) OF PDUSessionResourceSetupItemSURes
PDUSessionResourceSetupItemSURes ::= SEQUENCE {
pDUSessionID PDUSessionID,
pDUSessionResourceSetupResponseTransfer OCTET STRING (CONTAINING PDUSessionResourceSetupResponseTransfer),
iE-Extensions ProtocolExtensionContainer { {PDUSessionResourceSetupItemSURes-ExtIEs} } OPTIONAL,
...
}
PDUSessionResourceSetupItemSURes-ExtIEs NGAP-PROTOCOL-EXTENSION ::= {
...
}
PDUSessionResourceSetupRequestTransfer ::= SEQUENCE {
protocolIEs ProtocolIE-Container { {PDUSessionResourceSetupRequestTransferIEs} },
...
}
PDUSessionResourceSetupRequestTransferIEs NGAP-PROTOCOL-IES ::= {
{ ID id-PDUSessionAggregateMaximumBitRate CRITICALITY reject TYPE PDUSessionAggregateMaximumBitRate PRESENCE optional }|
{ ID id-UL-NGU-UP-TNLInformation CRITICALITY reject TYPE UPTransportLayerInformation PRESENCE mandatory }|
{ ID id-AdditionalUL-NGU-UP-TNLInformation CRITICALITY reject TYPE UPTransportLayerInformationList PRESENCE optional }|
{ ID id-DataForwardingNotPossible CRITICALITY reject TYPE DataForwardingNotPossible PRESENCE optional }|
{ ID id-PDUSessionType CRITICALITY reject TYPE PDUSessionType PRESENCE mandatory }|
{ ID id-SecurityIndication CRITICALITY reject TYPE SecurityIndication PRESENCE optional }|
{ ID id-NetworkInstance CRITICALITY reject TYPE NetworkInstance PRESENCE optional }|
{ ID id-QosFlowSetupRequestList CRITICALITY reject TYPE QosFlowSetupRequestList PRESENCE mandatory }|
{ ID id-CommonNetworkInstance CRITICALITY ignore TYPE CommonNetworkInstance PRESENCE optional }|
{ ID id-DirectForwardingPathAvailability CRITICALITY ignore TYPE DirectForwardingPathAvailability PRESENCE optional }|
{ ID id-RedundantUL-NGU-UP-TNLInformation CRITICALITY ignore TYPE UPTransportLayerInformation PRESENCE optional }|
{ ID id-AdditionalRedundantUL-NGU-UP-TNLInformation CRITICALITY ignore TYPE UPTransportLayerInformationList PRESENCE optional }|
{ ID id-RedundantCommonNetworkInstance CRITICALITY ignore TYPE CommonNetworkInstance PRESENCE optional }|
{ ID id-RedundantPDUSessionInformation CRITICALITY ignore TYPE RedundantPDUSessionInformation PRESENCE optional }|
{ ID id-MBSSessionSetupRequestList CRITICALITY ignore TYPE MBSSessionSetupRequestList PRESENCE optional }|
{ ID id-DownlinkTLContainer CRITICALITY ignore TYPE TLContainer PRESENCE optional },
...
}
PDUSessionResourceSetupResponseTransfer ::= SEQUENCE {
dLQosFlowPerTNLInformation QosFlowPerTNLInformation,
additionalDLQosFlowPerTNLInformation QosFlowPerTNLInformationList OPTIONAL,
securityResult SecurityResult OPTIONAL,
qosFlowFailedToSetupList QosFlowListWithCause OPTIONAL,
iE-Extensions ProtocolExtensionContainer { {PDUSessionResourceSetupResponseTransfer-ExtIEs} } OPTIONAL,
...
}
PDUSessionResourceSetupResponseTransfer-ExtIEs NGAP-PROTOCOL-EXTENSION ::= {
{ ID id-RedundantDLQosFlowPerTNLInformation CRITICALITY ignore EXTENSION QosFlowPerTNLInformation PRESENCE optional }|
{ ID id-AdditionalRedundantDLQosFlowPerTNLInformation CRITICALITY ignore EXTENSION QosFlowPerTNLInformationList PRESENCE optional }|
{ ID id-UsedRSNInformation CRITICALITY ignore EXTENSION RedundantPDUSessionInformation PRESENCE optional }|
{ ID id-GlobalRANNodeID CRITICALITY ignore EXTENSION GlobalRANNodeID PRESENCE optional }|
{ ID id-MBS-SupportIndicator CRITICALITY ignore EXTENSION MBS-SupportIndicator PRESENCE optional }|
{ ID id-MBSSessionSetupResponseList CRITICALITY ignore EXTENSION MBSSessionSetupResponseList PRESENCE optional }|
{ ID id-MBSSessionFailedtoSetupList CRITICALITY ignore EXTENSION MBSSessionFailedtoSetupList PRESENCE optional }|
{ ID id-QoSFlowTSCList CRITICALITY ignore EXTENSION QoSFlowTSCList PRESENCE optional }|
{ ID id-UplinkTLContainer CRITICALITY ignore EXTENSION TLContainer PRESENCE optional }|
{ ID id-ECNMarkingorCongestionInformationReportingStatus CRITICALITY ignore EXTENSION ECNMarkingorCongestionInformationReportingStatus PRESENCE optional }|
{ ID id-PDUSetbasedHandlingIndicator CRITICALITY ignore EXTENSION PDUSetbasedHandlingIndicator PRESENCE optional },
...
}
PDUSessionResourceSetupUnsuccessfulTransfer ::= SEQUENCE {
cause Cause,
criticalityDiagnostics CriticalityDiagnostics OPTIONAL,
iE-Extensions ProtocolExtensionContainer { {PDUSessionResourceSetupUnsuccessfulTransfer-ExtIEs} } OPTIONAL,
...
}
PDUSessionResourceSetupUnsuccessfulTransfer-ExtIEs NGAP-PROTOCOL-EXTENSION ::= {
...
}
PDUSessionResourceSuspendListSUSReq ::= SEQUENCE (SIZE(1..maxnoofPDUSessions)) OF PDUSessionResourceSuspendItemSUSReq
PDUSessionResourceSuspendItemSUSReq ::= SEQUENCE {
pDUSessionID PDUSessionID,
uEContextSuspendRequestTransfer OCTET STRING (CONTAINING UEContextSuspendRequestTransfer),
iE-Extensions ProtocolExtensionContainer { {PDUSessionResourceSuspendItemSUSReq-ExtIEs} } OPTIONAL,
...
}
PDUSessionResourceSuspendItemSUSReq-ExtIEs NGAP-PROTOCOL-EXTENSION ::= {
...
}
PDUSessionResourceSwitchedList ::= SEQUENCE (SIZE(1..maxnoofPDUSessions)) OF PDUSessionResourceSwitchedItem
PDUSessionResourceSwitchedItem ::= SEQUENCE {
pDUSessionID PDUSessionID,
pathSwitchRequestAcknowledgeTransfer OCTET STRING (CONTAINING PathSwitchRequestAcknowledgeTransfer),
iE-Extensions ProtocolExtensionContainer { { PDUSessionResourceSwitchedItem-ExtIEs} } OPTIONAL,
...
}
PDUSessionResourceSwitchedItem-ExtIEs NGAP-PROTOCOL-EXTENSION ::= {
{ ID id-PduSessionExpectedUEActivityBehaviour CRITICALITY ignore EXTENSION ExpectedUEActivityBehaviour PRESENCE optional },
...
}
PDUSessionResourceToBeSwitchedDLList ::= SEQUENCE (SIZE(1..maxnoofPDUSessions)) OF PDUSessionResourceToBeSwitchedDLItem
PDUSessionResourceToBeSwitchedDLItem ::= SEQUENCE {
pDUSessionID PDUSessionID,
pathSwitchRequestTransfer OCTET STRING (CONTAINING PathSwitchRequestTransfer),
iE-Extensions ProtocolExtensionContainer { { PDUSessionResourceToBeSwitchedDLItem-ExtIEs} } OPTIONAL,
...
}
PDUSessionResourceToBeSwitchedDLItem-ExtIEs NGAP-PROTOCOL-EXTENSION ::= {
...
}
PDUSessionResourceToReleaseListHOCmd ::= SEQUENCE (SIZE(1..maxnoofPDUSessions)) OF PDUSessionResourceToReleaseItemHOCmd
PDUSessionResourceToReleaseItemHOCmd ::= SEQUENCE {
pDUSessionID PDUSessionID,
handoverPreparationUnsuccessfulTransfer OCTET STRING (CONTAINING HandoverPreparationUnsuccessfulTransfer),
iE-Extensions ProtocolExtensionContainer { {PDUSessionResourceToReleaseItemHOCmd-ExtIEs} } OPTIONAL,
...
}
PDUSessionResourceToReleaseItemHOCmd-ExtIEs NGAP-PROTOCOL-EXTENSION ::= {
...
}
PDUSessionResourceToReleaseListRelCmd ::= SEQUENCE (SIZE(1..maxnoofPDUSessions)) OF PDUSessionResourceToReleaseItemRelCmd
PDUSessionResourceToReleaseItemRelCmd ::= SEQUENCE {
pDUSessionID PDUSessionID,
pDUSessionResourceReleaseCommandTransfer OCTET STRING (CONTAINING PDUSessionResourceReleaseCommandTransfer),
iE-Extensions ProtocolExtensionContainer { {PDUSessionResourceToReleaseItemRelCmd-ExtIEs} } OPTIONAL,
...
}
PDUSessionResourceToReleaseItemRelCmd-ExtIEs NGAP-PROTOCOL-EXTENSION ::= {
...
}
PDUSessionType ::= ENUMERATED {
ipv4,
ipv6,
ipv4v6,
ethernet,
unstructured,
...
}
PDUSessionUsageReport ::= SEQUENCE {
rATType ENUMERATED {nr, eutra, ..., nr-unlicensed, e-utra-unlicensed},
pDUSessionTimedReportList VolumeTimedReportList,
iE-Extensions ProtocolExtensionContainer { {PDUSessionUsageReport-ExtIEs} } OPTIONAL,
...
}
PDUSessionUsageReport-ExtIEs NGAP-PROTOCOL-EXTENSION ::= {
...
}
PDUsetQoSParameters ::= SEQUENCE {
ulPDUSetQoSInformation PDUsetQoSInformation OPTIONAL,
dlPDUSetQoSInformation PDUsetQoSInformation OPTIONAL,
iE-Extensions ProtocolExtensionContainer { { PDUsetQoSParameters-ExtIEs } } OPTIONAL,
...
}
PDUsetQoSParameters-ExtIEs NGAP-PROTOCOL-EXTENSION ::= {
...
}
PDUsetQoSInformation ::= SEQUENCE {
pduSetDelayBudget ExtendedPacketDelayBudget OPTIONAL,
pduSetErrorRate PacketErrorRate OPTIONAL,
pduSetIntegratedHandlingInformation ENUMERATED {true, false, ...} OPTIONAL,
iE-Extensions ProtocolExtensionContainer { { PDUsetQoSInformation-ExtIEs } } OPTIONAL,
...
}
PDUsetQoSInformation-ExtIEs NGAP-PROTOCOL-EXTENSION ::= {
...
}
PDUSetbasedHandlingIndicator ::= ENUMERATED {supported, ...}
PEIPSassistanceInformation ::= SEQUENCE {
cNsubgroupID CNsubgroupID,
iE-Extensions ProtocolExtensionContainer { {PEIPSassistanceInformation-ExtIEs} } OPTIONAL,
...
}
PEIPSassistanceInformation-ExtIEs NGAP-PROTOCOL-EXTENSION ::= {
...
}
Periodicity ::= INTEGER (0..640000, ...)
PeriodicityBound ::= SEQUENCE {
periodicityLowerBound Periodicity,
periodicityUpperBound Periodicity,
iE-Extensions ProtocolExtensionContainer { {PeriodicityBound-ExtIEs} } OPTIONAL,
...
}
PeriodicityBound-ExtIEs NGAP-PROTOCOL-EXTENSION ::= {
...
}
PeriodicityList ::= SEQUENCE {
allowedPeriodicityList AllowedPeriodicityList,
iE-Extensions ProtocolExtensionContainer { {PeriodicityList-ExtIEs} } OPTIONAL,
...
}
PeriodicityList-ExtIEs NGAP-PROTOCOL-EXTENSION ::= {
...
}
AllowedPeriodicityList ::= SEQUENCE (SIZE(1..maxnoofPeriodicities)) OF Periodicity
PeriodicityRange ::= CHOICE {
periodicityBound PeriodicityBound,
periodicityList AllowedPeriodicityList,
choice-extensions ProtocolIE-SingleContainer { {PeriodicityRange-ExtIEs} }
}
PeriodicityRange-ExtIEs NGAP-PROTOCOL-IES ::= {
...
}
PeriodicRegistrationUpdateTimer ::= BIT STRING (SIZE(8))
PLMNIdentity ::= OCTET STRING (SIZE(3))
PLMNAreaBasedQMC ::= SEQUENCE {
plmnListforQMC PLMNListforQMC,
iE-Extensions ProtocolExtensionContainer { {PLMNAreaBasedQMC-ExtIEs} } OPTIONAL,
...
}
PLMNAreaBasedQMC-ExtIEs NGAP-PROTOCOL-EXTENSION ::= {
...
}
PLMNListforQMC ::= SEQUENCE (SIZE(1..maxnoofPLMNforQMC)) OF PLMNIdentity
PLMNSupportList ::= SEQUENCE (SIZE(1..maxnoofPLMNs)) OF PLMNSupportItem
PLMNSupportItem ::= SEQUENCE {
pLMNIdentity PLMNIdentity,
sliceSupportList SliceSupportList,
iE-Extensions ProtocolExtensionContainer { {PLMNSupportItem-ExtIEs} } OPTIONAL,
...
}
PLMNSupportItem-ExtIEs NGAP-PROTOCOL-EXTENSION ::= {
{ ID id-NPN-Support CRITICALITY reject EXTENSION NPN-Support PRESENCE optional }|
{ ID id-ExtendedSliceSupportList CRITICALITY reject EXTENSION ExtendedSliceSupportList PRESENCE optional }|
{ ID id-OnboardingSupport CRITICALITY ignore EXTENSION OnboardingSupport PRESENCE optional },
...
}
PNI-NPN-MobilityInformation ::= SEQUENCE {
allowed-PNI-NPI-List Allowed-PNI-NPN-List,
iE-Extensions ProtocolExtensionContainer { {PNI-NPN-MobilityInformation-ExtIEs} } OPTIONAL,
...
}
PNI-NPN-MobilityInformation-ExtIEs NGAP-PROTOCOL-EXTENSION ::= {
...
}
PortNumber ::= OCTET STRING (SIZE(2))
Pre-emptionCapability ::= ENUMERATED {
shall-not-trigger-pre-emption,
may-trigger-pre-emption,
...
}
Pre-emptionVulnerability ::= ENUMERATED {
not-pre-emptable,
pre-emptable,
...
}
PriorityLevelARP ::= INTEGER (1..15)
PriorityLevelQos ::= INTEGER (1..127, ...)
PWSFailedCellIDList ::= CHOICE {
eUTRA-CGI-PWSFailedList EUTRA-CGIList,
nR-CGI-PWSFailedList NR-CGIList,
choice-Extensions ProtocolIE-SingleContainer { {PWSFailedCellIDList-ExtIEs} }
}
PWSFailedCellIDList-ExtIEs NGAP-PROTOCOL-IES ::= {
...
}
PNI-NPN-AreaScopeofMDT ::= SEQUENCE {
cAGListforMDT CAGListforMDT,
iE-Extensions ProtocolExtensionContainer { {PNI-NPN-AreaScopeofMDT-ExtIEs} } OPTIONAL,
...
}
PNI-NPN-AreaScopeofMDT-ExtIEs NGAP-PROTOCOL-EXTENSION ::= {
...
}
PNI-NPNBasedMDT::= SEQUENCE {
cAGListforMDT CAGListforMDT,
iE-Extensions ProtocolExtensionContainer { {PNI-NPNBasedMDT-ExtIEs} } OPTIONAL,
...
}
PNI-NPNBasedMDT-ExtIEs NGAP-PROTOCOL-EXTENSION ::= {
...
}
-- Q
QMCConfigInfo ::= SEQUENCE {
uEAppLayerMeasInfoList UEAppLayerMeasInfoList,
iE-Extensions ProtocolExtensionContainer { { QMCConfigInfo-ExtIEs} } OPTIONAL,
...
}
QMCConfigInfo-ExtIEs NGAP-PROTOCOL-EXTENSION ::= {
...
}
QMCDeactivation ::= SEQUENCE {
qoEReferenceList QoEReferenceList,
iE-Extensions ProtocolExtensionContainer { { QMCDeactivation-ExtIEs} } OPTIONAL,
...
}
QMCDeactivation-ExtIEs NGAP-PROTOCOL-EXTENSION ::= {
...
}
QoEReferenceList ::= SEQUENCE (SIZE(1..maxnoofUEAppLayerMeas)) OF QoEReference
QoEReference ::= OCTET STRING (SIZE(6))
QoERVQoEReportingPaths ::= SEQUENCE {
qoEReportingPath ENUMERATED{srb4, srb5, ...} OPTIONAL,
rVQoEReportingPath ENUMERATED{srb4, srb5, ...} OPTIONAL,
iE-Extensions ProtocolExtensionContainer { {QoERVQoEReportingPaths-ExtIEs} } OPTIONAL,
...
}
QoERVQoEReportingPaths-ExtIEs NGAP-PROTOCOL-EXTENSION ::= {
...
}
QosCharacteristics ::= CHOICE {
nonDynamic5QI NonDynamic5QIDescriptor,
dynamic5QI Dynamic5QIDescriptor,
choice-Extensions ProtocolIE-SingleContainer { {QosCharacteristics-ExtIEs} }
}
QosCharacteristics-ExtIEs NGAP-PROTOCOL-IES ::= {
...
}
QosFlowAcceptedList ::= SEQUENCE (SIZE(1..maxnoofQosFlows)) OF QosFlowAcceptedItem
QosFlowAcceptedItem ::= SEQUENCE {
qosFlowIdentifier QosFlowIdentifier,
iE-Extensions ProtocolExtensionContainer { {QosFlowAcceptedItem-ExtIEs} } OPTIONAL,
...
}
QosFlowAcceptedItem-ExtIEs NGAP-PROTOCOL-EXTENSION ::= {
{ ID id-CurrentQoSParaSetIndex CRITICALITY ignore EXTENSION AlternativeQoSParaSetIndex PRESENCE optional },
...
}
QosFlowAdditionalInfoListRelCom ::= SEQUENCE (SIZE(1..maxnoofQosFlows)) OF QosFlowAdditionalInfoItemRelCom
QosFlowAdditionalInfoItemRelCom ::= SEQUENCE {
qosFlowIdentifier QosFlowIdentifier,
downlinkTLContainer TLContainer OPTIONAL,
iE-Extensions ProtocolExtensionContainer { {QosFlowAdditionalInfoItemRelCom-ExtIEs} } OPTIONAL,
...
}
QosFlowAdditionalInfoItemRelCom-ExtIEs NGAP-PROTOCOL-EXTENSION ::= {
...
}
QosFlowAdditionalInfoListRelRes ::= SEQUENCE (SIZE(1..maxnoofQosFlows)) OF QosFlowAdditionalInfoItemRelRes
QosFlowAdditionalInfoItemRelRes ::= SEQUENCE {
qosFlowIdentifier QosFlowIdentifier,
uplinkTLContainer TLContainer OPTIONAL,
iE-Extensions ProtocolExtensionContainer { {QosFlowAdditionalInfoItemRelRes-ExtIEs} } OPTIONAL,
...
}
QosFlowAdditionalInfoItemRelRes-ExtIEs NGAP-PROTOCOL-EXTENSION ::= {
...
}
QosFlowAddOrModifyRequestList ::= SEQUENCE (SIZE(1..maxnoofQosFlows)) OF QosFlowAddOrModifyRequestItem
QosFlowAddOrModifyRequestItem ::= SEQUENCE {
qosFlowIdentifier QosFlowIdentifier,
qosFlowLevelQosParameters QosFlowLevelQosParameters OPTIONAL,
e-RAB-ID E-RAB-ID OPTIONAL,
iE-Extensions ProtocolExtensionContainer { {QosFlowAddOrModifyRequestItem-ExtIEs} } OPTIONAL,
...
}
QosFlowAddOrModifyRequestItem-ExtIEs NGAP-PROTOCOL-EXTENSION ::= {
{ID id-TSCTrafficCharacteristics CRITICALITY ignore EXTENSION TSCTrafficCharacteristics PRESENCE optional }|
{ID id-RedundantQosFlowIndicator CRITICALITY ignore EXTENSION RedundantQosFlowIndicator PRESENCE optional }|
{ID id-UL-NGU-UP-TNLInformation CRITICALITY ignore EXTENSION UPTransportLayerInformation PRESENCE optional }|
{ID id-DownlinkTLContainer CRITICALITY ignore EXTENSION TLContainer PRESENCE optional }|
{ID id-ECNMarkingorCongestionInformationReportingRequest CRITICALITY ignore EXTENSION ECNMarkingorCongestionInformationReportingRequest PRESENCE optional },
...
}
QosFlowAddOrModifyResponseList ::= SEQUENCE (SIZE(1..maxnoofQosFlows)) OF QosFlowAddOrModifyResponseItem
QosFlowAddOrModifyResponseItem ::= SEQUENCE {
qosFlowIdentifier QosFlowIdentifier,
iE-Extensions ProtocolExtensionContainer { {QosFlowAddOrModifyResponseItem-ExtIEs} } OPTIONAL,
...
}
QosFlowAddOrModifyResponseItem-ExtIEs NGAP-PROTOCOL-EXTENSION ::= {
{ ID id-CurrentQoSParaSetIndex CRITICALITY ignore EXTENSION AlternativeQoSParaSetIndex PRESENCE optional }|
{ ID id-TSCTrafficCharacteristicsFeedback CRITICALITY ignore EXTENSION TSCTrafficCharacteristicsFeedback PRESENCE optional }|
{ ID id-UplinkTLContainer CRITICALITY ignore EXTENSION TLContainer PRESENCE optional }|
{ ID id-DL-NGU-UP-TNLInformation CRITICALITY ignore EXTENSION UPTransportLayerInformation PRESENCE optional }|
{ ID id-ANPacketDelayBudgetUL CRITICALITY ignore EXTENSION ExtendedPacketDelayBudget PRESENCE optional },
...
}
QosFlowFeedbackList ::= SEQUENCE (SIZE(1..maxnoofQosFlows)) OF QosFlowFeedbackItem
QosFlowFeedbackItem ::= SEQUENCE {
qosFlowIdentifier QosFlowIdentifier,
updateFeedback UpdateFeedback OPTIONAL,
cNpacketDelayBudgetDL ExtendedPacketDelayBudget OPTIONAL,
cNpacketDelayBudgetUL ExtendedPacketDelayBudget OPTIONAL,
iE-Extensions ProtocolExtensionContainer { {QosFlowFeedbackItem-ExtIEs} } OPTIONAL,
...
}
QosFlowFeedbackItem-ExtIEs NGAP-PROTOCOL-EXTENSION ::= {
...
}
QosFlowIdentifier ::= INTEGER (0..63, ...)
QosFlowInformationList ::= SEQUENCE (SIZE(1..maxnoofQosFlows)) OF QosFlowInformationItem
QosFlowInformationItem ::= SEQUENCE {
qosFlowIdentifier QosFlowIdentifier,
dLForwarding DLForwarding OPTIONAL,
iE-Extensions ProtocolExtensionContainer { {QosFlowInformationItem-ExtIEs} } OPTIONAL,
...
}
QosFlowInformationItem-ExtIEs NGAP-PROTOCOL-EXTENSION ::= {
{ID id-ULForwarding CRITICALITY ignore EXTENSION ULForwarding PRESENCE optional}|
{ID id-SourceTNLAddrInfo CRITICALITY ignore EXTENSION TransportLayerAddress PRESENCE optional}|
{ID id-SourceNodeTNLAddrInfo CRITICALITY ignore EXTENSION TransportLayerAddress PRESENCE optional},
...
}
QosFlowLevelQosParameters ::= SEQUENCE {
qosCharacteristics QosCharacteristics,
allocationAndRetentionPriority AllocationAndRetentionPriority,
gBR-QosInformation GBR-QosInformation OPTIONAL,
reflectiveQosAttribute ReflectiveQosAttribute OPTIONAL,
additionalQosFlowInformation AdditionalQosFlowInformation OPTIONAL,
iE-Extensions ProtocolExtensionContainer { {QosFlowLevelQosParameters-ExtIEs} } OPTIONAL,
...
}
QosFlowLevelQosParameters-ExtIEs NGAP-PROTOCOL-EXTENSION ::= {
{ID id-QosMonitoringRequest CRITICALITY ignore EXTENSION QosMonitoringRequest PRESENCE optional}|
{ID id-QosMonitoringReportingFrequency CRITICALITY ignore EXTENSION QosMonitoringReportingFrequency PRESENCE optional}|
{ID id-PDUsetQoSParameters CRITICALITY ignore EXTENSION PDUsetQoSParameters PRESENCE optional},
...
}
QosMonitoringRequest ::= ENUMERATED {ul, dl, both, ..., stop}
QosMonitoringReportingFrequency ::= INTEGER (1..1800, ...)
QoSFlowList ::= SEQUENCE (SIZE(1..maxnoofQosFlows)) OF QosFlowIdentifier
QosFlowListWithCause ::= SEQUENCE (SIZE(1..maxnoofQosFlows)) OF QosFlowWithCauseItem
QosFlowWithCauseItem ::= SEQUENCE {
qosFlowIdentifier QosFlowIdentifier,
cause Cause,
iE-Extensions ProtocolExtensionContainer { {QosFlowWithCauseItem-ExtIEs} } OPTIONAL,
...
}
QosFlowWithCauseItem-ExtIEs NGAP-PROTOCOL-EXTENSION ::= {
...
}
QosFlowModifyConfirmList ::= SEQUENCE (SIZE(1..maxnoofQosFlows)) OF QosFlowModifyConfirmItem
QosFlowModifyConfirmItem ::= SEQUENCE {
qosFlowIdentifier QosFlowIdentifier,
iE-Extensions ProtocolExtensionContainer { {QosFlowModifyConfirmItem-ExtIEs} } OPTIONAL,
...
}
QosFlowModifyConfirmItem-ExtIEs NGAP-PROTOCOL-EXTENSION ::= {
...
}
QosFlowNotifyList ::= SEQUENCE (SIZE(1..maxnoofQosFlows)) OF QosFlowNotifyItem
QosFlowNotifyItem ::= SEQUENCE {
qosFlowIdentifier QosFlowIdentifier,
notificationCause NotificationCause,
iE-Extensions ProtocolExtensionContainer { {QosFlowNotifyItem-ExtIEs} } OPTIONAL,
...
}
QosFlowNotifyItem-ExtIEs NGAP-PROTOCOL-EXTENSION ::= {
{ ID id-CurrentQoSParaSetIndex CRITICALITY ignore EXTENSION AlternativeQoSParaSetNotifyIndex PRESENCE optional }|
{ ID id-TSCTrafficCharacteristicsFeedback CRITICALITY ignore EXTENSION TSCTrafficCharacteristicsFeedback PRESENCE optional },
...
}
QosFlowParametersList ::= SEQUENCE (SIZE(1..maxnoofQosFlows)) OF QosFlowParametersItem
QosFlowParametersItem ::= SEQUENCE {
qosFlowIdentifier QosFlowIdentifier,
alternativeQoSParaSetList AlternativeQoSParaSetList OPTIONAL,
iE-Extensions ProtocolExtensionContainer { {QosFlowParametersItem-ExtIEs} } OPTIONAL,
...
}
QosFlowParametersItem-ExtIEs NGAP-PROTOCOL-EXTENSION ::= {
{ ID id-CNPacketDelayBudgetDL CRITICALITY ignore EXTENSION ExtendedPacketDelayBudget PRESENCE optional }|
{ ID id-CNPacketDelayBudgetUL CRITICALITY ignore EXTENSION ExtendedPacketDelayBudget PRESENCE optional }|
{ ID id-BurstArrivalTimeDownlink CRITICALITY ignore EXTENSION BurstArrivalTime PRESENCE optional },
...
}
QosFlowPerTNLInformation ::= SEQUENCE {
uPTransportLayerInformation UPTransportLayerInformation,
associatedQosFlowList AssociatedQosFlowList,
iE-Extensions ProtocolExtensionContainer { { QosFlowPerTNLInformation-ExtIEs} } OPTIONAL,
...
}
QosFlowPerTNLInformation-ExtIEs NGAP-PROTOCOL-EXTENSION ::= {
...
}
QosFlowPerTNLInformationList ::= SEQUENCE (SIZE(1..maxnoofMultiConnectivityMinusOne)) OF QosFlowPerTNLInformationItem
QosFlowPerTNLInformationItem ::= SEQUENCE {
qosFlowPerTNLInformation QosFlowPerTNLInformation,
iE-Extensions ProtocolExtensionContainer { { QosFlowPerTNLInformationItem-ExtIEs} } OPTIONAL,
...
}
QosFlowPerTNLInformationItem-ExtIEs NGAP-PROTOCOL-EXTENSION ::= {
...
}
QosFlowSetupRequestList ::= SEQUENCE (SIZE(1..maxnoofQosFlows)) OF QosFlowSetupRequestItem
QosFlowSetupRequestItem ::= SEQUENCE {
qosFlowIdentifier QosFlowIdentifier,
qosFlowLevelQosParameters QosFlowLevelQosParameters,
e-RAB-ID E-RAB-ID OPTIONAL,
iE-Extensions ProtocolExtensionContainer { {QosFlowSetupRequestItem-ExtIEs} } OPTIONAL,
...
}
QosFlowSetupRequestItem-ExtIEs NGAP-PROTOCOL-EXTENSION ::= {
{ID id-TSCTrafficCharacteristics CRITICALITY ignore EXTENSION TSCTrafficCharacteristics PRESENCE optional }|
{ID id-RedundantQosFlowIndicator CRITICALITY ignore EXTENSION RedundantQosFlowIndicator PRESENCE optional }|
{ID id-ECNMarkingorCongestionInformationReportingRequest CRITICALITY ignore EXTENSION ECNMarkingorCongestionInformationReportingRequest PRESENCE optional },
...
}
QosFlowListWithDataForwarding ::= SEQUENCE (SIZE(1..maxnoofQosFlows)) OF QosFlowItemWithDataForwarding
QosFlowItemWithDataForwarding ::= SEQUENCE {
qosFlowIdentifier QosFlowIdentifier,
dataForwardingAccepted DataForwardingAccepted OPTIONAL,
iE-Extensions ProtocolExtensionContainer { {QosFlowItemWithDataForwarding-ExtIEs} } OPTIONAL,
...
}
QosFlowItemWithDataForwarding-ExtIEs NGAP-PROTOCOL-EXTENSION ::= {
{ ID id-CurrentQoSParaSetIndex CRITICALITY ignore EXTENSION AlternativeQoSParaSetIndex PRESENCE optional },
...
}
QosFlowToBeForwardedList ::= SEQUENCE (SIZE(1..maxnoofQosFlows)) OF QosFlowToBeForwardedItem
QosFlowToBeForwardedItem ::= SEQUENCE {
qosFlowIdentifier QosFlowIdentifier,
iE-Extensions ProtocolExtensionContainer { {QosFlowToBeForwardedItem-ExtIEs} } OPTIONAL,
...
}
QosFlowToBeForwardedItem-ExtIEs NGAP-PROTOCOL-EXTENSION ::= {
...
}
QoSFlowTSCList ::= SEQUENCE (SIZE(1..maxnoofQosFlows)) OF QoSFlowTSCItem
QoSFlowTSCItem ::= SEQUENCE {
qosFlowIdentifier QosFlowIdentifier,
tSCTrafficCharacteristicsFeedback TSCTrafficCharacteristicsFeedback OPTIONAL,
aNPacketDelayBudgetUL ExtendedPacketDelayBudget OPTIONAL,
iE-Extensions ProtocolExtensionContainer { {QoSFlowTSCItem-ExtIEs} } OPTIONAL,
...
}
QoSFlowTSCItem-ExtIEs NGAP-PROTOCOL-EXTENSION ::= {
...
}
QoSFlowsUsageReportList ::= SEQUENCE (SIZE(1..maxnoofQosFlows)) OF QoSFlowsUsageReport-Item
QoSFlowsUsageReport-Item ::= SEQUENCE {
qosFlowIdentifier QosFlowIdentifier,
rATType ENUMERATED {nr, eutra, ..., nr-unlicensed, e-utra-unlicensed},
qoSFlowsTimedReportList VolumeTimedReportList,
iE-Extensions ProtocolExtensionContainer { {QoSFlowsUsageReport-Item-ExtIEs} } OPTIONAL,
...
}
QoSFlowsUsageReport-Item-ExtIEs NGAP-PROTOCOL-EXTENSION ::= {
...
}
-- R
RANfeedbacktype ::= CHOICE {
proactive RANfeedbacktype-proactive,
reactive RANfeedbacktype-reactive,
choice-extensions ProtocolIE-SingleContainer { {RANfeedbacktype-ExtIEs} }
}
RANfeedbacktype-ExtIEs NGAP-PROTOCOL-IES ::= {
...
}
RANfeedbacktype-proactive ::= SEQUENCE {
burstArrivalTimeWindow BurstArrivalTimeWindow,
periodicityRange PeriodicityRange OPTIONAL,
iE-Extension ProtocolExtensionContainer { {RANfeedbacktype-proactive-ExtIEs} } OPTIONAL,
...
}
RANfeedbacktype-proactive-ExtIEs NGAP-PROTOCOL-EXTENSION ::= {
...
}
RANfeedbacktype-reactive ::= SEQUENCE {
capabilityForBATAdaptation ENUMERATED {true, ...},
iE-Extension ProtocolExtensionContainer { {RANfeedbacktype-reactive-ExtIEs} } OPTIONAL,
...
}
RANfeedbacktype-reactive-ExtIEs NGAP-PROTOCOL-EXTENSION ::= {
...
}
Range ::= ENUMERATED {m50, m80, m180, m200, m350, m400, m500, m700, m1000, ...}
RANNodeName ::= PrintableString (SIZE(1..150, ...))
RANNodeNameVisibleString ::= VisibleString (SIZE(1..150, ...))
RANNodeNameUTF8String ::= UTF8String (SIZE(1..150, ...))
RANPagingPriority ::= INTEGER (1..256)
RANStatusTransfer-TransparentContainer ::= SEQUENCE {
dRBsSubjectToStatusTransferList DRBsSubjectToStatusTransferList,
iE-Extensions ProtocolExtensionContainer { {RANStatusTransfer-TransparentContainer-ExtIEs} } OPTIONAL,
...
}
RANStatusTransfer-TransparentContainer-ExtIEs NGAP-PROTOCOL-EXTENSION ::= {
...
}
RANTimingSynchronisationStatusInfo ::= SEQUENCE {
synchronisationState ENUMERATED {locked, holdover, freerun, ...} OPTIONAL,
traceabletoUTC ENUMERATED {true, false, ...} OPTIONAL,
traceabletoGNSS ENUMERATED {true, false, ...} OPTIONAL,
clockFrequencyStability BIT STRING (SIZE(16)) OPTIONAL,
clockAccuracy ClockAccuracy OPTIONAL,
parentTImeSource ParentTImeSource OPTIONAL,
iE-Extensions ProtocolExtensionContainer { {RANTimingSynchronisationStatusInfo-ExtIEs} } OPTIONAL,
...
}
RANTimingSynchronisationStatusInfo-ExtIEs NGAP-PROTOCOL-EXTENSION ::= {
...
}
RAN-TSSRequestType ::= ENUMERATED {start, stop, ...}
RAN-TSSScope ::= CHOICE {
rANNodeLevel GlobalGNB-ID,
cellListLevel RANTSSCellList,
choice-Extensions ProtocolIE-SingleContainer { { RAN-TSSScope-ExtIEs} }
}
RAN-TSSScope-ExtIEs NGAP-PROTOCOL-IES ::= {
...
}
RANTSSCellList ::= SEQUENCE (SIZE(1..maxnoofCellsTSS)) OF RANTSSCellItem
RANTSSCellItem ::= SEQUENCE {
nRCGI NR-CGI,
iE-Extensions ProtocolExtensionContainer { {RANTSSCellItem-ExtIEs} } OPTIONAL,
...
}
RANTSSCellItem-ExtIEs NGAP-PROTOCOL-EXTENSION ::= {
...
}
RAN-UE-NGAP-ID ::= INTEGER (0..4294967295)
RAT-Information ::= ENUMERATED {
unlicensed,
nb-IoT,
...,
nR-LEO,
nR-MEO,
nR-GEO,
nR-OTHERSAT
}
RATRestrictions ::= SEQUENCE (SIZE(1..maxnoofEPLMNsPlusOne)) OF RATRestrictions-Item
RATRestrictions-Item ::= SEQUENCE {
pLMNIdentity PLMNIdentity,
rATRestrictionInformation RATRestrictionInformation,
iE-Extensions ProtocolExtensionContainer { {RATRestrictions-Item-ExtIEs} } OPTIONAL,
...
}
RATRestrictions-Item-ExtIEs NGAP-PROTOCOL-EXTENSION ::= {
{ ID id-ExtendedRATRestrictionInformation CRITICALITY ignore EXTENSION ExtendedRATRestrictionInformation PRESENCE optional },
...
}
RATRestrictionInformation ::= BIT STRING (SIZE(8, ...))
RecommendedCellsForPaging ::= SEQUENCE {
recommendedCellList RecommendedCellList,
iE-Extensions ProtocolExtensionContainer { {RecommendedCellsForPaging-ExtIEs} } OPTIONAL,
...
}
RecommendedCellsForPaging-ExtIEs NGAP-PROTOCOL-EXTENSION ::= {
...
}
RecommendedCellList ::= SEQUENCE (SIZE(1..maxnoofRecommendedCells)) OF RecommendedCellItem
RecommendedCellItem ::= SEQUENCE {
nGRAN-CGI NGRAN-CGI,
timeStayedInCell INTEGER (0..4095) OPTIONAL,
iE-Extensions ProtocolExtensionContainer { {RecommendedCellItem-ExtIEs} } OPTIONAL,
...
}
RecommendedCellItem-ExtIEs NGAP-PROTOCOL-EXTENSION ::= {
...
}
RecommendedRANNodesForPaging ::= SEQUENCE {
recommendedRANNodeList RecommendedRANNodeList,
iE-Extensions ProtocolExtensionContainer { {RecommendedRANNodesForPaging-ExtIEs} } OPTIONAL,
...
}
RecommendedRANNodesForPaging-ExtIEs NGAP-PROTOCOL-EXTENSION ::= {
...
}
RecommendedRANNodeList::= SEQUENCE (SIZE(1..maxnoofRecommendedRANNodes)) OF RecommendedRANNodeItem
RecommendedRANNodeItem ::= SEQUENCE {
aMFPagingTarget AMFPagingTarget,
iE-Extensions ProtocolExtensionContainer { {RecommendedRANNodeItem-ExtIEs} } OPTIONAL,
...
}
RecommendedRANNodeItem-ExtIEs NGAP-PROTOCOL-EXTENSION ::= {
...
}
RedCapIndication ::= ENUMERATED {
redcap,
...
}
RedirectionVoiceFallback ::= ENUMERATED {
possible,
not-possible,
...
}
RedundantPDUSessionInformation ::= SEQUENCE {
rSN RSN,
iE-Extensions ProtocolExtensionContainer { {RedundantPDUSessionInformation-ExtIEs} } OPTIONAL,
...
}
RedundantPDUSessionInformation-ExtIEs NGAP-PROTOCOL-EXTENSION ::= {
{ ID id-PDUSessionPairID CRITICALITY ignore EXTENSION PDUSessionPairID PRESENCE optional },
...
}
RedundantQosFlowIndicator ::= ENUMERATED {true, false}
ReflectiveQosAttribute ::= ENUMERATED {
subject-to,
...
}
RelativeAMFCapacity ::= INTEGER (0..255)
ReportArea ::= ENUMERATED {
cell,
...
}
RepetitionPeriod ::= INTEGER (0..131071)
ResetAll ::= ENUMERATED {
reset-all,
...
}
ReportAmountMDT ::= ENUMERATED {
r1, r2, r4, r8, r16, r32, r64, rinfinity
}
ReportIntervalMDT ::= ENUMERATED {
ms120, ms240, ms480, ms640, ms1024, ms2048, ms5120, ms10240, min1, min6, min12, min30, min60
}
ExtendedReportIntervalMDT ::= ENUMERATED {
ms20480, ms40960, ...
}
ResetType ::= CHOICE {
nG-Interface ResetAll,
partOfNG-Interface UE-associatedLogicalNG-connectionList,
choice-Extensions ProtocolIE-SingleContainer { {ResetType-ExtIEs} }
}
ResetType-ExtIEs NGAP-PROTOCOL-IES ::= {
...
}
RGLevelWirelineAccessCharacteristics ::= OCTET STRING
RNC-ID ::= INTEGER (0..4095)
RoutingID ::= OCTET STRING
RRCContainer ::= OCTET STRING
RRCEstablishmentCause ::= ENUMERATED {
emergency,
highPriorityAccess,
mt-Access,
mo-Signalling,
mo-Data,
mo-VoiceCall,
mo-VideoCall,
mo-SMS,
mps-PriorityAccess,
mcs-PriorityAccess,
...,
notAvailable,
mo-ExceptionData
}
RRCInactiveTransitionReportRequest ::= ENUMERATED {
subsequent-state-transition-report,
single-rrc-connected-state-report,
cancel-report,
...
}
RRCState ::= ENUMERATED {
inactive,
connected,
...
}
RSN ::= ENUMERATED {v1, v2, ...}
RIMInformationTransfer ::= SEQUENCE {
targetRANNodeID-RIM TargetRANNodeID-RIM,
sourceRANNodeID SourceRANNodeID,
rIMInformation RIMInformation,
iE-Extensions ProtocolExtensionContainer { {RIMInformationTransfer-ExtIEs} } OPTIONAL,
...
}
RIMInformationTransfer-ExtIEs NGAP-PROTOCOL-EXTENSION ::= {
...
}
RIMInformation ::= SEQUENCE {
targetgNBSetID GNBSetID,
rIM-RSDetection ENUMERATED {rs-detected, rs-disappeared, ...},
iE-Extensions ProtocolExtensionContainer { {RIMInformation-ExtIEs} } OPTIONAL,
...
}
RIMInformation-ExtIEs NGAP-PROTOCOL-EXTENSION ::= {
...
}
GNBSetID ::= BIT STRING (SIZE(22))
RSPPQoSFlowList ::= SEQUENCE (SIZE(1..maxnoofRSPPQoSFlows)) OF RSPPQoSFlowItem
RSPPQoSFlowItem ::= SEQUENCE {
pQI FiveQI,
rSPPFlowBitRates RSPPFlowBitRates OPTIONAL,
range Range OPTIONAL,
iE-Extensions ProtocolExtensionContainer { { RSPPQoSFlowItem-ExtIEs} } OPTIONAL,
...
}
RSPPQoSFlowItem-ExtIEs NGAP-PROTOCOL-EXTENSION ::= {
...
}
RSPPFlowBitRates ::= SEQUENCE {
guaranteedFlowBitRate BitRate,
maximumFlowBitRate BitRate,
iE-Extensions ProtocolExtensionContainer { { RSPPFlowBitRates-ExtIEs} } OPTIONAL,
...
}
RSPPFlowBitRates-ExtIEs NGAP-PROTOCOL-EXTENSION ::= {
...
}
-- S
ScheduledCommunicationTime ::= SEQUENCE {
dayofWeek BIT STRING (SIZE(7)) OPTIONAL,
timeofDayStart INTEGER (0..86399, ...) OPTIONAL,
timeofDayEnd INTEGER (0..86399, ...) OPTIONAL,
iE-Extensions ProtocolExtensionContainer { { ScheduledCommunicationTime-ExtIEs}} OPTIONAL,
...
}
ScheduledCommunicationTime-ExtIEs NGAP-PROTOCOL-EXTENSION ::= {
...
}
SCTP-TLAs ::= SEQUENCE (SIZE(1..maxnoofXnTLAs)) OF TransportLayerAddress
SD ::= OCTET STRING (SIZE(3))
SecondaryRATUsageInformation ::= SEQUENCE {
pDUSessionUsageReport PDUSessionUsageReport OPTIONAL,
qosFlowsUsageReportList QoSFlowsUsageReportList OPTIONAL,
iE-Extension ProtocolExtensionContainer { {SecondaryRATUsageInformation-ExtIEs} } OPTIONAL,
...
}
SecondaryRATUsageInformation-ExtIEs NGAP-PROTOCOL-EXTENSION ::= {
...
}
SecondaryRATDataUsageReportTransfer ::= SEQUENCE {
secondaryRATUsageInformation SecondaryRATUsageInformation OPTIONAL,
iE-Extensions ProtocolExtensionContainer { {SecondaryRATDataUsageReportTransfer-ExtIEs} } OPTIONAL,
...
}
SecondaryRATDataUsageReportTransfer-ExtIEs NGAP-PROTOCOL-EXTENSION ::= {
...
}
SecurityContext ::= SEQUENCE {
nextHopChainingCount NextHopChainingCount,
nextHopNH SecurityKey,
iE-Extensions ProtocolExtensionContainer { {SecurityContext-ExtIEs} } OPTIONAL,
...
}
SecurityContext-ExtIEs NGAP-PROTOCOL-EXTENSION ::= {
...
}
SecurityIndication ::= SEQUENCE {
integrityProtectionIndication IntegrityProtectionIndication,
confidentialityProtectionIndication ConfidentialityProtectionIndication,
maximumIntegrityProtectedDataRate-UL MaximumIntegrityProtectedDataRate OPTIONAL,
-- The above IE shall be present if the Integrity Protection Indication IE is set to the value "required" or "preferred"
iE-Extensions ProtocolExtensionContainer { {SecurityIndication-ExtIEs} } OPTIONAL,
...
}
SecurityIndication-ExtIEs NGAP-PROTOCOL-EXTENSION ::= {
{ ID id-MaximumIntegrityProtectedDataRate-DL CRITICALITY ignore EXTENSION MaximumIntegrityProtectedDataRate PRESENCE optional },
...
}
SecurityKey ::= BIT STRING (SIZE(256))
SecurityResult ::= SEQUENCE {
integrityProtectionResult IntegrityProtectionResult,
confidentialityProtectionResult ConfidentialityProtectionResult,
iE-Extensions ProtocolExtensionContainer { {SecurityResult-ExtIEs} } OPTIONAL,
...
}
SecurityResult-ExtIEs NGAP-PROTOCOL-EXTENSION ::= {
...
}
SensorMeasurementConfiguration ::= SEQUENCE {
sensorMeasConfig SensorMeasConfig,
sensorMeasConfigNameList SensorMeasConfigNameList OPTIONAL,
iE-Extensions ProtocolExtensionContainer { {SensorMeasurementConfiguration-ExtIEs} } OPTIONAL,
...
}
SensorMeasurementConfiguration-ExtIEs NGAP-PROTOCOL-EXTENSION ::= {
...
}
SensorMeasConfigNameList ::= SEQUENCE (SIZE(1..maxnoofSensorName)) OF SensorMeasConfigNameItem
SensorMeasConfigNameItem ::= SEQUENCE {
sensorNameConfig SensorNameConfig,
iE-Extensions ProtocolExtensionContainer { { SensorMeasConfigNameItem-ExtIEs } } OPTIONAL,
...
}
SensorMeasConfigNameItem-ExtIEs NGAP-PROTOCOL-EXTENSION ::= {
...
}
SensorMeasConfig::= ENUMERATED {setup,...}
SensorNameConfig ::= CHOICE {
uncompensatedBarometricConfig ENUMERATED {true, ...},
ueSpeedConfig ENUMERATED {true, ...},
ueOrientationConfig ENUMERATED {true, ...},
choice-Extensions ProtocolIE-SingleContainer { {SensorNameConfig-ExtIEs} }
}
SensorNameConfig-ExtIEs NGAP-PROTOCOL-IES ::= {
...
}
SerialNumber ::= BIT STRING (SIZE(16))
ServedGUAMIList ::= SEQUENCE (SIZE(1..maxnoofServedGUAMIs)) OF ServedGUAMIItem
ServedGUAMIItem ::= SEQUENCE {
gUAMI GUAMI,
backupAMFName AMFName OPTIONAL,
iE-Extensions ProtocolExtensionContainer { {ServedGUAMIItem-ExtIEs} } OPTIONAL,
...
}
ServedGUAMIItem-ExtIEs NGAP-PROTOCOL-EXTENSION ::= {
{ID id-GUAMIType CRITICALITY ignore EXTENSION GUAMIType PRESENCE optional }|
{ID id-ExtendedBackupAMFName CRITICALITY ignore EXTENSION Extended-AMFName PRESENCE optional},
...
}
ServiceAreaInformation ::= SEQUENCE (SIZE(1.. maxnoofEPLMNsPlusOne)) OF ServiceAreaInformation-Item
ServiceAreaInformation-Item ::= SEQUENCE {
pLMNIdentity PLMNIdentity,
allowedTACs AllowedTACs OPTIONAL,
notAllowedTACs NotAllowedTACs OPTIONAL,
iE-Extensions ProtocolExtensionContainer { {ServiceAreaInformation-Item-ExtIEs} } OPTIONAL,
...
}
ServiceAreaInformation-Item-ExtIEs NGAP-PROTOCOL-EXTENSION ::= {
...
}
ServiceType ::= ENUMERATED {streaming, mTSI, vR, ...}
SgNB-UE-X2AP-ID ::= INTEGER (0..4294967295)
SharedNGU-MulticastTNLInformation ::= SEQUENCE {
iP-MulticastAddress TransportLayerAddress,
iP-SourceAddress TransportLayerAddress,
gTP-TEID GTP-TEID,
iE-Extensions ProtocolExtensionContainer { {SharedNGU-MulticastTNLInformation-ExtIEs} } OPTIONAL,
...
}
SharedNGU-MulticastTNLInformation-ExtIEs NGAP-PROTOCOL-EXTENSION ::= {
...
}
SliceOverloadList ::= SEQUENCE (SIZE(1..maxnoofSliceItems)) OF SliceOverloadItem
SliceOverloadItem ::= SEQUENCE {
s-NSSAI S-NSSAI,
iE-Extensions ProtocolExtensionContainer { {SliceOverloadItem-ExtIEs} } OPTIONAL,
...
}
SliceOverloadItem-ExtIEs NGAP-PROTOCOL-EXTENSION ::= {
...
}
SliceSupportList ::= SEQUENCE (SIZE(1..maxnoofSliceItems)) OF SliceSupportItem
SliceSupportItem ::= SEQUENCE {
s-NSSAI S-NSSAI,
iE-Extensions ProtocolExtensionContainer { {SliceSupportItem-ExtIEs} } OPTIONAL,
...
}
SliceSupportItem-ExtIEs NGAP-PROTOCOL-EXTENSION ::= {
...
}
SliceSupportListQMC ::= SEQUENCE (SIZE(1..maxnoofSNSSAIforQMC)) OF SliceSupportQMC-Item
SliceSupportQMC-Item ::= SEQUENCE {
s-NSSAI S-NSSAI,
iE-Extensions ProtocolExtensionContainer { {SliceSupportQMC-Item-ExtIEs} } OPTIONAL,
...
}
SliceSupportQMC-Item-ExtIEs NGAP-PROTOCOL-EXTENSION ::= {
...
}
SNPN-MobilityInformation ::= SEQUENCE {
serving-NID NID,
iE-Extensions ProtocolExtensionContainer { {SNPN-MobilityInformation-ExtIEs} } OPTIONAL,
...
}
SNPN-MobilityInformation-ExtIEs NGAP-PROTOCOL-EXTENSION ::= {
{ID id-EquivalentSNPNsList CRITICALITY reject EXTENSION EquivalentSNPNsList PRESENCE optional},
...
}
S-NSSAI ::= SEQUENCE {
sST SST,
sD SD OPTIONAL,
iE-Extensions ProtocolExtensionContainer { { S-NSSAI-ExtIEs} } OPTIONAL,
...
}
S-NSSAI-ExtIEs NGAP-PROTOCOL-EXTENSION ::= {
...
}
SONConfigurationTransfer ::= SEQUENCE {
targetRANNodeID-SON TargetRANNodeID-SON,
sourceRANNodeID SourceRANNodeID,
sONInformation SONInformation,
xnTNLConfigurationInfo XnTNLConfigurationInfo OPTIONAL,
-- The above IE shall be present if the SON Information IE contains the SON Information Request IE set to the value "Xn TNL Configuration Info"
iE-Extensions ProtocolExtensionContainer { {SONConfigurationTransfer-ExtIEs} } OPTIONAL,
...
}
SONConfigurationTransfer-ExtIEs NGAP-PROTOCOL-EXTENSION ::= {
...
}
SONInformation ::= CHOICE {
sONInformationRequest SONInformationRequest,
sONInformationReply SONInformationReply,
choice-Extensions ProtocolIE-SingleContainer { {SONInformation-ExtIEs} }
}
SONInformation-ExtIEs NGAP-PROTOCOL-IES ::= {
{ ID id-SONInformationReport CRITICALITY ignore TYPE SONInformationReport PRESENCE mandatory },
...
}
SONInformationReply ::= SEQUENCE {
xnTNLConfigurationInfo XnTNLConfigurationInfo OPTIONAL,
iE-Extensions ProtocolExtensionContainer { {SONInformationReply-ExtIEs} } OPTIONAL,
...
}
SONInformationReply-ExtIEs NGAP-PROTOCOL-EXTENSION ::= {
...
}
SONInformationReport::= CHOICE {
failureIndicationInformation FailureIndication,
hOReportInformation HOReport,
choice-Extensions ProtocolIE-SingleContainer { { SONInformationReport-ExtIEs} }
}
SONInformationReport-ExtIEs NGAP-PROTOCOL-IES ::= {
{ ID id-SuccessfulHandoverReportList CRITICALITY ignore TYPE SuccessfulHandoverReportList PRESENCE mandatory }|
{ ID id-SuccessfulPSCellChangeReportList CRITICALITY ignore TYPE SuccessfulPSCellChangeReportList PRESENCE mandatory },
...
}
SNPN-CellBasedMDT::= SEQUENCE {
sNPNcellIdListforMDT SNPNCellIdListforMDT,
iE-Extensions ProtocolExtensionContainer { {SNPN-CellBasedMDT-ExtIEs} } OPTIONAL,
...
}
SNPN-CellBasedMDT-ExtIEs NGAP-PROTOCOL-EXTENSION ::= {
...
}
SNPNCellIdListforMDT ::= SEQUENCE (SIZE(1..maxnoofCellIDforMDT)) OF SNPNCellIdListforMDTItem
SNPNCellIdListforMDTItem ::= SEQUENCE {
nR-CGI NR-CGI,
nID NID,
iE-Extensions ProtocolExtensionContainer {{ SNPNCellIdListforMDTItem-ExtIEs}} OPTIONAL,
...
}
SNPNCellIdListforMDTItem-ExtIEs NGAP-PROTOCOL-EXTENSION ::= {
...
}
SNPN-TAIBasedMDT::= SEQUENCE {
sNPNTAIListforMDT SNPNTAIListforMDT,
iE-Extensions ProtocolExtensionContainer { {SNPN-TAIBasedMDT-ExtIEs} } OPTIONAL,
...
}
SNPN-TAIBasedMDT-ExtIEs NGAP-PROTOCOL-EXTENSION ::= {
...
}
SNPNTAIListforMDT ::= SEQUENCE (SIZE(1.. maxnoofTAforMDT)) OF SNPNTAIListforMDTItem
SNPNTAIListforMDTItem ::= SEQUENCE {
tAI TAI,
nID NID,
iE-Extensions ProtocolExtensionContainer {{ SNPNTAIListforMDTItem-ExtIEs}} OPTIONAL,
...
}
SNPNTAIListforMDTItem-ExtIEs NGAP-PROTOCOL-EXTENSION ::= {
...
}
SNPN-BasedMDT::= SEQUENCE {
sNPNListforMDT SNPNListforMDT,
iE-Extensions ProtocolExtensionContainer { {SNPN-BasedMDT-ExtIEs} } OPTIONAL,
...
}
SNPN-BasedMDT-ExtIEs NGAP-PROTOCOL-EXTENSION ::= {
...
}
SNPNListforMDT ::= SEQUENCE (SIZE(1.. maxnoofMDTSNPNs)) OF SNPNListforMDTItem
SNPNListforMDTItem ::= SEQUENCE {
pLMNIdentity PLMNIdentity,
nID NID,
iE-Extensions ProtocolExtensionContainer {{ SNPNListforMDTItem-ExtIEs}} OPTIONAL,
...
}
SNPNListforMDTItem-ExtIEs NGAP-PROTOCOL-EXTENSION ::= {
...
}
-- --------------------------------------------------------------------
-- SON Information Report
-- --------------------------------------------------------------------
SuccessfulHandoverReportList ::= SEQUENCE (SIZE(1..maxnoofSuccessfulHOReports)) OF SuccessfulHandoverReport-Item
SuccessfulHandoverReport-Item ::= SEQUENCE {
successfulHOReportContainer OCTET STRING,
iE-Extensions ProtocolExtensionContainer { { SuccessfulHandoverReport-Item-ExtIEs} } OPTIONAL,
...
}
SuccessfulHandoverReport-Item-ExtIEs NGAP-PROTOCOL-EXTENSION ::= {
...
}
SuccessfulPSCellChangeReportList ::= SEQUENCE (SIZE(1..maxnoofSuccessfulPSCellChangeReports)) OF SuccessfulPSCellChangeReport-Item
SuccessfulPSCellChangeReport-Item ::= SEQUENCE {
successfulPSCellChangeReportContainer OCTET STRING,
iE-Extensions ProtocolExtensionContainer { { SuccessfulPSCellChangeReport-Item-ExtIEs} } OPTIONAL,
...
}
SuccessfulPSCellChangeReport-Item-ExtIEs NGAP-PROTOCOL-EXTENSION ::= {
...
}
SONInformationRequest ::= ENUMERATED {
xn-TNL-configuration-info,
...
}
SourceNGRANNode-ToTargetNGRANNode-TransparentContainer ::= SEQUENCE {
rRCContainer RRCContainer,
pDUSessionResourceInformationList PDUSessionResourceInformationList OPTIONAL,
e-RABInformationList E-RABInformationList OPTIONAL,
targetCell-ID NGRAN-CGI,
indexToRFSP IndexToRFSP OPTIONAL,
uEHistoryInformation UEHistoryInformation,
iE-Extensions ProtocolExtensionContainer { {SourceNGRANNode-ToTargetNGRANNode-TransparentContainer-ExtIEs} } OPTIONAL,
...
}
SourceNGRANNode-ToTargetNGRANNode-TransparentContainer-ExtIEs NGAP-PROTOCOL-EXTENSION ::= {
{ ID id-SgNB-UE-X2AP-ID CRITICALITY ignore EXTENSION SgNB-UE-X2AP-ID PRESENCE optional }|
{ ID id-UEHistoryInformationFromTheUE CRITICALITY ignore EXTENSION UEHistoryInformationFromTheUE PRESENCE optional }|
{ ID id-SourceNodeID CRITICALITY ignore EXTENSION SourceNodeID PRESENCE optional }|
{ ID id-UEContextReferenceAtSource CRITICALITY ignore EXTENSION RAN-UE-NGAP-ID PRESENCE optional }|
{ ID id-MBS-ActiveSessionInformation-SourcetoTargetList CRITICALITY ignore EXTENSION MBS-ActiveSessionInformation-SourcetoTargetList PRESENCE optional }|
{ ID id-QMCConfigInfo CRITICALITY ignore EXTENSION QMCConfigInfo PRESENCE optional }|
{ ID id-NGAPIESupportInformationRequestList CRITICALITY ignore EXTENSION NGAPIESupportInformationRequestList PRESENCE optional }|
{ ID id-CandidateRelayUEInformationList CRITICALITY reject EXTENSION CandidateRelayUEInformationList PRESENCE optional }|
{ ID id-TimeBasedHandoverInformation CRITICALITY ignore EXTENSION TimeBasedHandoverInformation PRESENCE optional }|
{ ID id-SourceSN-to-TargetSN-QMCInfo CRITICALITY ignore EXTENSION QMCConfigInfo PRESENCE optional },
...
}
SourceNodeID ::= CHOICE {
sourceengNB-ID GlobalGNB-ID,
choice-Extensions ProtocolIE-SingleContainer { { SourceNodeID-ExtIEs} }
}
SourceNodeID-ExtIEs NGAP-PROTOCOL-IES ::= {
...
}
SourceOfUEActivityBehaviourInformation ::= ENUMERATED {
subscription-information,
statistics,
...
}
SourceRANNodeID ::= SEQUENCE {
globalRANNodeID GlobalRANNodeID,
selectedTAI TAI,
iE-Extensions ProtocolExtensionContainer { {SourceRANNodeID-ExtIEs} } OPTIONAL,
...
}
SourceRANNodeID-ExtIEs NGAP-PROTOCOL-EXTENSION ::= {
...
}
SourceToTarget-TransparentContainer ::= OCTET STRING
-- This IE includes a transparent container from the source RAN node to the target RAN node.
-- The octets of the OCTET STRING are encoded according to the specifications of the target system.
SourceToTarget-AMFInformationReroute ::= SEQUENCE {
configuredNSSAI ConfiguredNSSAI OPTIONAL,
rejectedNSSAIinPLMN RejectedNSSAIinPLMN OPTIONAL,
rejectedNSSAIinTA RejectedNSSAIinTA OPTIONAL,
iE-Extensions ProtocolExtensionContainer { {SourceToTarget-AMFInformationReroute-ExtIEs} } OPTIONAL,
...
}
SourceToTarget-AMFInformationReroute-ExtIEs NGAP-PROTOCOL-EXTENSION ::= {
...
}
-- This IE includes information from the source Core node to the target Core node for reroute information provide by NSSF.
-- The octets of the OCTET STRING are encoded according to the specifications of the Core network.
SRVCCOperationPossible ::= ENUMERATED {
possible,
notPossible,
...
}
ConfiguredNSSAI ::= OCTET STRING (SIZE(128))
RejectedNSSAIinPLMN ::= OCTET STRING (SIZE(32))
RejectedNSSAIinTA ::= OCTET STRING (SIZE(32))
SST ::= OCTET STRING (SIZE(1))
SupportedTAList ::= SEQUENCE (SIZE(1..maxnoofTACs)) OF SupportedTAItem
SupportedTAItem ::= SEQUENCE {
tAC TAC,
broadcastPLMNList BroadcastPLMNList,
iE-Extensions ProtocolExtensionContainer { {SupportedTAItem-ExtIEs} } OPTIONAL,
...
}
SupportedTAItem-ExtIEs NGAP-PROTOCOL-EXTENSION ::= {
{ID id-ConfiguredTACIndication CRITICALITY ignore EXTENSION ConfiguredTACIndication PRESENCE optional }|
{ID id-RAT-Information CRITICALITY reject EXTENSION RAT-Information PRESENCE optional },
...
}
SuspendIndicator ::= ENUMERATED {
true,
...
}
Suspend-Request-Indication ::= ENUMERATED {
suspend-requested,
...
}
Suspend-Response-Indication ::= ENUMERATED {
suspend-indicated,
...
}
SurvivalTime ::= INTEGER (0..1920000, ...)
SLPositioningRangingServiceInfo ::= SEQUENCE{
sLPositioningRangingAuthorized SLPositioningRangingAuthorized,
sLPositioningRangingQoSParameters SLPositioningRangingQoSParameters OPTIONAL,
iE-Extensions ProtocolExtensionContainer { {SLPositioningRangingServiceInfo-ExtIEs} } OPTIONAL,
...
}
SLPositioningRangingServiceInfo-ExtIEs NGAP-PROTOCOL-EXTENSION ::= {
...
}
SLPositioningRangingAuthorized ::= ENUMERATED {
authorized,
not-authorized,
...
}
SLPositioningRangingQoSParameters ::= SEQUENCE {
rSPPQoSFlowList RSPPQoSFlowList,
rSPPLinkAggregateBitRates BitRate OPTIONAL,
iE-Extensions ProtocolExtensionContainer { { SLPositioningRangingQoSParameters-ExtIEs} } OPTIONAL,
...
}
SLPositioningRangingQoSParameters-ExtIEs NGAP-PROTOCOL-EXTENSION ::= {
...
}
-- T
TAC ::= OCTET STRING (SIZE(3))
TACListInNRNTN ::= SEQUENCE (SIZE(1..maxnoofTACsinNTN)) OF TAC
TAI ::= SEQUENCE {
pLMNIdentity PLMNIdentity,
tAC TAC,
iE-Extensions ProtocolExtensionContainer { {TAI-ExtIEs} } OPTIONAL,
...
}
TAI-ExtIEs NGAP-PROTOCOL-EXTENSION ::= {
...
}
TAIBroadcastEUTRA ::= SEQUENCE (SIZE(1..maxnoofTAIforWarning)) OF TAIBroadcastEUTRA-Item
TAIBroadcastEUTRA-Item ::= SEQUENCE {
tAI TAI,
completedCellsInTAI-EUTRA CompletedCellsInTAI-EUTRA,
iE-Extensions ProtocolExtensionContainer { {TAIBroadcastEUTRA-Item-ExtIEs} } OPTIONAL,
...
}
TAIBroadcastEUTRA-Item-ExtIEs NGAP-PROTOCOL-EXTENSION ::= {
...
}
TAIBroadcastNR ::= SEQUENCE (SIZE(1..maxnoofTAIforWarning)) OF TAIBroadcastNR-Item
TAIBroadcastNR-Item ::= SEQUENCE {
tAI TAI,
completedCellsInTAI-NR CompletedCellsInTAI-NR,
iE-Extensions ProtocolExtensionContainer { {TAIBroadcastNR-Item-ExtIEs} } OPTIONAL,
...
}
TAIBroadcastNR-Item-ExtIEs NGAP-PROTOCOL-EXTENSION ::= {
...
}
TAICancelledEUTRA ::= SEQUENCE (SIZE(1..maxnoofTAIforWarning)) OF TAICancelledEUTRA-Item
TAICancelledEUTRA-Item ::= SEQUENCE {
tAI TAI,
cancelledCellsInTAI-EUTRA CancelledCellsInTAI-EUTRA,
iE-Extensions ProtocolExtensionContainer { {TAICancelledEUTRA-Item-ExtIEs} } OPTIONAL,
...
}
TAICancelledEUTRA-Item-ExtIEs NGAP-PROTOCOL-EXTENSION ::= {
...
}
TAICancelledNR ::= SEQUENCE (SIZE(1..maxnoofTAIforWarning)) OF TAICancelledNR-Item
TAICancelledNR-Item ::= SEQUENCE {
tAI TAI,
cancelledCellsInTAI-NR CancelledCellsInTAI-NR,
iE-Extensions ProtocolExtensionContainer { {TAICancelledNR-Item-ExtIEs} } OPTIONAL,
...
}
TAICancelledNR-Item-ExtIEs NGAP-PROTOCOL-EXTENSION ::= {
...
}
TAIListForInactive ::= SEQUENCE (SIZE(1..maxnoofTAIforInactive)) OF TAIListForInactiveItem
TAIListForInactiveItem ::= SEQUENCE {
tAI TAI,
iE-Extensions ProtocolExtensionContainer { {TAIListForInactiveItem-ExtIEs} } OPTIONAL,
...
}
TAIListForInactiveItem-ExtIEs NGAP-PROTOCOL-EXTENSION ::= {
...
}
TAIListForPaging ::= SEQUENCE (SIZE(1..maxnoofTAIforPaging)) OF TAIListForPagingItem
TAIListForPagingItem ::= SEQUENCE {
tAI TAI,
iE-Extensions ProtocolExtensionContainer { {TAIListForPagingItem-ExtIEs} } OPTIONAL,
...
}
TAIListForPagingItem-ExtIEs NGAP-PROTOCOL-EXTENSION ::= {
...
}
TAIListForRestart ::= SEQUENCE (SIZE(1..maxnoofTAIforRestart)) OF TAI
TAIListForWarning ::= SEQUENCE (SIZE(1..maxnoofTAIforWarning)) OF TAI
TAINSAGSupportList ::= SEQUENCE (SIZE(1..maxnoofNSAGs)) OF TAINSAGSupportItem
TAINSAGSupportItem ::= SEQUENCE {
nSAG-ID NSAG-ID,
nSAGSliceSupportList ExtendedSliceSupportList,
iE-Extensions ProtocolExtensionContainer { {TAINSAGSupportItem-ExtIEs} } OPTIONAL,
...
}
TAINSAGSupportItem-ExtIEs NGAP-PROTOCOL-EXTENSION ::= {
...
}
TAIMBSSupportItem ::= SEQUENCE {
tAI TAI,
iE-Extensions ProtocolExtensionContainer { {TAIMBSSupportItem-ExtIEs} } OPTIONAL,
...
}
TAIMBSSupportItem-ExtIEs NGAP-PROTOCOL-EXTENSION ::= {
...
}
TAIMBSSupportList ::= SEQUENCE (SIZE(1..maxnoofSupportedTAIforMBS)) OF TAIMBSSupportItem
TargeteNB-ID ::= SEQUENCE {
globalENB-ID GlobalNgENB-ID,
selected-EPS-TAI EPS-TAI,
iE-Extensions ProtocolExtensionContainer { {TargeteNB-ID-ExtIEs} } OPTIONAL,
...
}
TargeteNB-ID-ExtIEs NGAP-PROTOCOL-EXTENSION ::= {
...
}
TargetHomeENB-ID ::= SEQUENCE {
pLMNidentity PLMNIdentity,
homeENB-ID BIT STRING (SIZE(28)),
selected-EPS-TAI EPS-TAI,
iE-Extensions ProtocolExtensionContainer { {TargetHomeENB-ID-ExtIEs} } OPTIONAL,
...
}
TargetHomeENB-ID-ExtIEs NGAP-PROTOCOL-EXTENSION ::= {
...
}
TargetID ::= CHOICE {
targetRANNodeID TargetRANNodeID,
targeteNB-ID TargeteNB-ID,
choice-Extensions ProtocolIE-SingleContainer { {TargetID-ExtIEs} }
}
TargetID-ExtIEs NGAP-PROTOCOL-IES ::= {
{ID id-TargetRNC-ID CRITICALITY reject TYPE TargetRNC-ID PRESENCE mandatory }|
{ID id-TargetHomeENB-ID CRITICALITY reject TYPE TargetHomeENB-ID PRESENCE mandatory },
...
}
TargetNGRANNode-ToSourceNGRANNode-TransparentContainer ::= SEQUENCE {
rRCContainer RRCContainer,
iE-Extensions ProtocolExtensionContainer { {TargetNGRANNode-ToSourceNGRANNode-TransparentContainer-ExtIEs} } OPTIONAL,
...
}
TargetNGRANNode-ToSourceNGRANNode-TransparentContainer-ExtIEs NGAP-PROTOCOL-EXTENSION ::= {
{ ID id-DAPSResponseInfoList CRITICALITY ignore EXTENSION DAPSResponseInfoList PRESENCE optional }|
{ ID id-DirectForwardingPathAvailability CRITICALITY ignore EXTENSION DirectForwardingPathAvailability PRESENCE optional }|
{ ID id-MBS-ActiveSessionInformation-TargettoSourceList CRITICALITY ignore EXTENSION MBS-ActiveSessionInformation-TargettoSourceList PRESENCE optional }|
{ ID id-NGAPIESupportInformationResponseList CRITICALITY ignore EXTENSION NGAPIESupportInformationResponseList PRESENCE optional },
...
}
TargetNGRANNode-ToSourceNGRANNode-FailureTransparentContainer ::= SEQUENCE {
cell-CAGInformation Cell-CAGInformation OPTIONAL,
iE-Extensions ProtocolExtensionContainer { {TargetNGRANNode-ToSourceNGRANNode-FailureTransparentContainer-ExtIEs} } OPTIONAL,
...
}
TargetNGRANNode-ToSourceNGRANNode-FailureTransparentContainer-ExtIEs NGAP-PROTOCOL-EXTENSION ::= {
{ ID id-NGAPIESupportInformationResponseList CRITICALITY ignore EXTENSION NGAPIESupportInformationResponseList PRESENCE optional },
...
}
TargetNSSAI ::= SEQUENCE (SIZE(1..maxnoofTargetS-NSSAIs)) OF TargetNSSAI-Item
TargetNSSAI-Item ::= SEQUENCE {
s-NSSAI S-NSSAI,
iE-Extensions ProtocolExtensionContainer { {TargetNSSAI-Item-ExtIEs} } OPTIONAL,
...
}
TargetNSSAI-Item-ExtIEs NGAP-PROTOCOL-EXTENSION ::= {
...
}
TargetNSSAIInformation ::= SEQUENCE {
targetNSSAI TargetNSSAI,
indexToRFSP IndexToRFSP,
iE-Extensions ProtocolExtensionContainer { {TargetNSSAIInformation-Item-ExtIEs} } OPTIONAL,
...
}
TargetNSSAIInformation-Item-ExtIEs NGAP-PROTOCOL-EXTENSION ::= {
...
}
TargetRANNodeID ::= SEQUENCE {
globalRANNodeID GlobalRANNodeID,
selectedTAI TAI,
iE-Extensions ProtocolExtensionContainer { {TargetRANNodeID-ExtIEs} } OPTIONAL,
...
}
TargetRANNodeID-ExtIEs NGAP-PROTOCOL-EXTENSION ::= {
{ID id-Selected-Target-SNPN-Identity CRITICALITY reject EXTENSION NID PRESENCE optional },
...
}
TargetRANNodeID-RIM ::= SEQUENCE {
globalRANNodeID GlobalRANNodeID,
selectedTAI TAI,
iE-Extensions ProtocolExtensionContainer { {TargetRANNodeID-RIM-ExtIEs} } OPTIONAL,
...
}
TargetRANNodeID-RIM-ExtIEs NGAP-PROTOCOL-EXTENSION ::= {
...
}
TargetRANNodeID-SON ::= SEQUENCE {
globalRANNodeID GlobalRANNodeID,
selectedTAI TAI,
iE-Extensions ProtocolExtensionContainer { {TargetRANNodeID-SON-ExtIEs} } OPTIONAL,
...
}
TargetRANNodeID-SON-ExtIEs NGAP-PROTOCOL-EXTENSION ::= {
{ID id-NR-CGI CRITICALITY ignore EXTENSION NR-CGI PRESENCE optional },
...
}
TargetRNC-ID ::= SEQUENCE {
lAI LAI,
rNC-ID RNC-ID,
extendedRNC-ID ExtendedRNC-ID OPTIONAL,
iE-Extensions ProtocolExtensionContainer { {TargetRNC-ID-ExtIEs} } OPTIONAL,
...
}
TargetRNC-ID-ExtIEs NGAP-PROTOCOL-EXTENSION ::= {
...
}
TargetToSource-TransparentContainer ::= OCTET STRING
-- This IE includes a transparent container from the target RAN node to the source RAN node.
-- The octets of the OCTET STRING are encoded according to the specifications of the target system.
TargettoSource-Failure-TransparentContainer ::= OCTET STRING
-- This IE includes a transparent container from the target RAN node to the source RAN node.
-- The octets of the OCTET STRING are encoded according to the specifications of the target system (if applicable).
TimeBasedHandoverInformation ::= SEQUENCE {
hOWindowStart HandoverWindowStart,
hOWindowDuration HandoverWindowDuration,
iE-Extensions ProtocolExtensionContainer { {TimeBasedHandoverInformation-ExtIEs} } OPTIONAL,
...
}
TimeBasedHandoverInformation-ExtIEs NGAP-PROTOCOL-EXTENSION ::= {
...
}
HandoverWindowStart ::= INTEGER (0..549755813887)
HandoverWindowDuration ::= INTEGER (1..6000)
TimerApproachForGUAMIRemoval ::= ENUMERATED {
apply-timer,
...
}
TimeSinceFailure ::= INTEGER (0..172800, ...)
TimeStamp ::= OCTET STRING (SIZE(4))
TimeSyncAssistanceInfo ::= SEQUENCE {
timeDistributionIndication ENUMERATED {enabled, disabled, ...},
uUTimeSyncErrorBudget INTEGER (1..1000000, ...) OPTIONAL,
-- The above IE shall be present if the Time Distribution Indication IE is set to the value "enabled"
iE-Extensions ProtocolExtensionContainer { {TimeSyncAssistanceInfo-ExtIEs} } OPTIONAL,
...
}
TimeSyncAssistanceInfo-ExtIEs NGAP-PROTOCOL-EXTENSION ::= {
{ ID id-ClockQualityReportingControlInfo CRITICALITY ignore EXTENSION ClockQualityReportingControlInfo PRESENCE optional},
...
}
TimeToWait ::= ENUMERATED {v1s, v2s, v5s, v10s, v20s, v60s, ...}
TimeUEStayedInCell ::= INTEGER (0..4095)
TimeUEStayedInCellEnhancedGranularity ::= INTEGER (0..40950)
TMGI ::= OCTET STRING (SIZE(6))
TNAP-ID ::= OCTET STRING
TNGF-ID ::= CHOICE {
tNGF-ID BIT STRING (SIZE(32, ...)),
choice-Extensions ProtocolIE-SingleContainer { {TNGF-ID-ExtIEs} }
}
TNGF-ID-ExtIEs NGAP-PROTOCOL-IES ::= {
...
}
TNLAddressWeightFactor ::= INTEGER (0..255)
TNLAssociationList ::= SEQUENCE (SIZE(1..maxnoofTNLAssociations)) OF TNLAssociationItem
TNLAssociationItem ::= SEQUENCE {
tNLAssociationAddress CPTransportLayerInformation,
cause Cause,
iE-Extensions ProtocolExtensionContainer { {TNLAssociationItem-ExtIEs} } OPTIONAL,
...
}
TNLAssociationItem-ExtIEs NGAP-PROTOCOL-EXTENSION ::= {
...
}
TNLAssociationUsage ::= ENUMERATED {
ue,
non-ue,
both,
...
}
TooearlyIntersystemHO::= SEQUENCE {
sourcecellID EUTRA-CGI,
failurecellID NGRAN-CGI,
uERLFReportContainer UERLFReportContainer OPTIONAL,
iE-Extensions ProtocolExtensionContainer { { TooearlyIntersystemHO-ExtIEs} } OPTIONAL,
...
}
TooearlyIntersystemHO-ExtIEs NGAP-PROTOCOL-EXTENSION ::= {
...
}
TraceActivation ::= SEQUENCE {
nGRANTraceID NGRANTraceID,
interfacesToTrace InterfacesToTrace,
traceDepth TraceDepth,
traceCollectionEntityIPAddress TransportLayerAddress,
iE-Extensions ProtocolExtensionContainer { {TraceActivation-ExtIEs} } OPTIONAL,
...
}
TraceActivation-ExtIEs NGAP-PROTOCOL-EXTENSION ::= {
{ ID id-MDTConfiguration CRITICALITY ignore EXTENSION MDT-Configuration PRESENCE optional }|
{ ID id-TraceCollectionEntityURI CRITICALITY ignore EXTENSION URI-address PRESENCE optional },
...
}
TraceDepth ::= ENUMERATED {
minimum,
medium,
maximum,
minimumWithoutVendorSpecificExtension,
mediumWithoutVendorSpecificExtension,
maximumWithoutVendorSpecificExtension,
...
}
TrafficLoadReductionIndication ::= INTEGER (1..99)
TransportLayerAddress ::= BIT STRING (SIZE(1..160, ...))
TypeOfError ::= ENUMERATED {
not-understood,
missing,
...
}
TAIBasedMDT ::= SEQUENCE {
tAIListforMDT TAIListforMDT,
iE-Extensions ProtocolExtensionContainer { {TAIBasedMDT-ExtIEs} } OPTIONAL,
...
}
TAIBasedMDT-ExtIEs NGAP-PROTOCOL-EXTENSION ::= {
...
}
TAIListforMDT ::= SEQUENCE (SIZE(1..maxnoofTAforMDT)) OF TAI
TAIBasedQMC ::= SEQUENCE {
tAIListforQMC TAIListforQMC,
iE-Extensions ProtocolExtensionContainer { {TAIBasedQMC-ExtIEs} } OPTIONAL,
...
}
TAIBasedQMC-ExtIEs NGAP-PROTOCOL-EXTENSION ::= {
...
}
TAIListforQMC ::= SEQUENCE (SIZE(1..maxnoofTAforQMC)) OF TAI
TABasedQMC ::= SEQUENCE {
tAListforQMC TAListforQMC,
iE-Extensions ProtocolExtensionContainer { {TABasedQMC-ExtIEs} } OPTIONAL,
...
}
TABasedQMC-ExtIEs NGAP-PROTOCOL-EXTENSION ::= {
...
}
TAListforQMC ::= SEQUENCE (SIZE(1..maxnoofTAforQMC)) OF TAC
TABasedMDT ::= SEQUENCE {
tAListforMDT TAListforMDT,
iE-Extensions ProtocolExtensionContainer { {TABasedMDT-ExtIEs} } OPTIONAL,
...
}
TABasedMDT-ExtIEs NGAP-PROTOCOL-EXTENSION ::= {
...
}
TAListforMDT ::= SEQUENCE (SIZE(1..maxnoofTAforMDT)) OF TAC
Threshold-RSRP ::= INTEGER(0..127)
Threshold-RSRQ ::= INTEGER(0..127)
Threshold-SINR ::= INTEGER(0..127)
TimeToTrigger ::= ENUMERATED {ms0, ms40, ms64, ms80, ms100, ms128, ms160, ms256, ms320, ms480, ms512, ms640, ms1024, ms1280, ms2560, ms5120}
TLContainer ::= OCTET STRING
TWAP-ID ::= OCTET STRING
TWIF-ID ::= CHOICE {
tWIF-ID BIT STRING (SIZE(32, ...)),
choice-Extensions ProtocolIE-SingleContainer { {TWIF-ID-ExtIEs} }
}
TWIF-ID-ExtIEs NGAP-PROTOCOL-IES ::= {
...
}
TSCAssistanceInformation ::= SEQUENCE {
periodicity Periodicity,
burstArrivalTime BurstArrivalTime OPTIONAL,
iE-Extensions ProtocolExtensionContainer { {TSCAssistanceInformation-ExtIEs} } OPTIONAL,
...
}
TSCAssistanceInformation-ExtIEs NGAP-PROTOCOL-EXTENSION ::= {
{ ID id-SurvivalTime CRITICALITY ignore EXTENSION SurvivalTime PRESENCE optional}|
{ ID id-RANfeedbacktype CRITICALITY ignore EXTENSION RANfeedbacktype PRESENCE optional}|
{ ID id-N6JitterInformation CRITICALITY ignore EXTENSION N6JitterInformation PRESENCE optional},
...
}
TSCTrafficCharacteristics ::= SEQUENCE {
tSCAssistanceInformationDL TSCAssistanceInformation OPTIONAL,
tSCAssistanceInformationUL TSCAssistanceInformation OPTIONAL,
iE-Extensions ProtocolExtensionContainer { {TSCTrafficCharacteristics-ExtIEs} } OPTIONAL,
...
}
TSCTrafficCharacteristics-ExtIEs NGAP-PROTOCOL-EXTENSION ::= {
...
}
TSCTrafficCharacteristicsFeedback ::= SEQUENCE {
tSCFeedbackInformationDL TSCFeedbackInformation OPTIONAL,
tSCFeedbackInformationUL TSCFeedbackInformation OPTIONAL,
iE-Extensions ProtocolExtensionContainer { { TSCTrafficCharacteristicsFeedback-ExtIEs} } OPTIONAL,
...
}
TSCTrafficCharacteristicsFeedback-ExtIEs NGAP-PROTOCOL-EXTENSION ::= {
...
}
TSCFeedbackInformation ::= SEQUENCE {
burstArrivalTimeOffset INTEGER (-640000..640000, ...),
adjustedPeriodicity Periodicity OPTIONAL,
iE-Extensions ProtocolExtensionContainer { { TSCFeedbackInformation-ExtIEs} } OPTIONAL,
...
}
TSCFeedbackInformation-ExtIEs NGAP-PROTOCOL-EXTENSION ::= {
...
}
-- U
UEAggregateMaximumBitRate ::= SEQUENCE {
uEAggregateMaximumBitRateDL BitRate,
uEAggregateMaximumBitRateUL BitRate,
iE-Extensions ProtocolExtensionContainer { {UEAggregateMaximumBitRate-ExtIEs} } OPTIONAL,
...
}
UEAggregateMaximumBitRate-ExtIEs NGAP-PROTOCOL-EXTENSION ::= {
...
}
UEAppLayerMeasInfoList ::= SEQUENCE (SIZE(1..maxnoofUEAppLayerMeas)) OF UEAppLayerMeasInfoItem
UEAppLayerMeasInfoItem ::= SEQUENCE {
uEAppLayerMeasConfigInfo UEAppLayerMeasConfigInfo,
iE-Extensions ProtocolExtensionContainer { { UEAppLayerMeasInfoItem-ExtIEs} } OPTIONAL,
...
}
UEAppLayerMeasInfoItem-ExtIEs NGAP-PROTOCOL-EXTENSION::= {
...
}
UEAppLayerMeasConfigInfo ::= SEQUENCE {
qoEReference QoEReference,
serviceType ServiceType,
areaScopeOfQMC AreaScopeOfQMC OPTIONAL,
measCollEntityIPAddress TransportLayerAddress,
qoEMeasurementStatus ENUMERATED {ongoing,...} OPTIONAL,
containerForAppLayerMeasConfig OCTET STRING (SIZE(1..8000)) OPTIONAL,
measConfigAppLayerID INTEGER (0..15, ...) OPTIONAL,
sliceSupportListQMC SliceSupportListQMC OPTIONAL,
mDT-AlignmentInfo MDT-AlignmentInfo OPTIONAL,
availableRANVisibleQoEMetrics AvailableRANVisibleQoEMetrics OPTIONAL,
iE-Extensions ProtocolExtensionContainer { { UEAppLayerMeasConfigInfo-ExtIEs} } OPTIONAL,
...
}
UEAppLayerMeasConfigInfo-ExtIEs NGAP-PROTOCOL-EXTENSION::= {
{ ID id-AssistanceInformationQoE-Meas CRITICALITY ignore EXTENSION AssistanceInformationQoE-Meas PRESENCE optional }|
{ ID id-CommServiceType CRITICALITY ignore EXTENSION CommServiceType PRESENCE optional }|
{ ID id-QoERVQoEReportingPaths CRITICALITY ignore EXTENSION QoERVQoEReportingPaths PRESENCE optional },
...
}
UE-associatedLogicalNG-connectionList ::= SEQUENCE (SIZE(1..maxnoofNGConnectionsToReset)) OF UE-associatedLogicalNG-connectionItem
UE-associatedLogicalNG-connectionItem ::= SEQUENCE {
aMF-UE-NGAP-ID AMF-UE-NGAP-ID OPTIONAL,
rAN-UE-NGAP-ID RAN-UE-NGAP-ID OPTIONAL,
iE-Extensions ProtocolExtensionContainer { {UE-associatedLogicalNG-connectionItem-ExtIEs} } OPTIONAL,
...
}
UE-associatedLogicalNG-connectionItem-ExtIEs NGAP-PROTOCOL-EXTENSION ::= {
...
}
UECapabilityInfoRequest ::= ENUMERATED {
requested,
...
}
UEContextRequest ::= ENUMERATED {requested, ...}
UEContextResumeRequestTransfer ::= SEQUENCE {
qosFlowFailedToResumeList QosFlowListWithCause OPTIONAL,
iE-Extensions ProtocolExtensionContainer { {UEContextResumeRequestTransfer-ExtIEs} } OPTIONAL,
...
}
UEContextResumeRequestTransfer-ExtIEs NGAP-PROTOCOL-EXTENSION ::= {
...
}
UEContextResumeResponseTransfer ::= SEQUENCE {
qosFlowFailedToResumeList QosFlowListWithCause OPTIONAL,
iE-Extensions ProtocolExtensionContainer { {UEContextResumeResponseTransfer-ExtIEs} } OPTIONAL,
...
}
UEContextResumeResponseTransfer-ExtIEs NGAP-PROTOCOL-EXTENSION ::= {
...
}
UEContextSuspendRequestTransfer ::= SEQUENCE {
suspendIndicator SuspendIndicator OPTIONAL,
iE-Extensions ProtocolExtensionContainer { {UEContextSuspendRequestTransfer-ExtIEs} } OPTIONAL,
...
}
UEContextSuspendRequestTransfer-ExtIEs NGAP-PROTOCOL-EXTENSION ::= {
...
}
UE-DifferentiationInfo ::= SEQUENCE {
periodicCommunicationIndicator ENUMERATED {periodically, ondemand, ... } OPTIONAL,
periodicTime INTEGER (1..3600, ...) OPTIONAL,
scheduledCommunicationTime ScheduledCommunicationTime OPTIONAL,
stationaryIndication ENUMERATED {stationary, mobile, ...} OPTIONAL,
trafficProfile ENUMERATED {single-packet, dual-packets, multiple-packets, ...} OPTIONAL,
batteryIndication ENUMERATED {battery-powered, battery-powered-not-rechargeable-or-replaceable, not-battery-powered, ...} OPTIONAL,
iE-Extensions ProtocolExtensionContainer { { UE-DifferentiationInfo-ExtIEs} } OPTIONAL,
...
}
UE-DifferentiationInfo-ExtIEs NGAP-PROTOCOL-EXTENSION ::= {
...
}
UEHistoryInformation ::= SEQUENCE (SIZE(1..maxnoofCellsinUEHistoryInfo)) OF LastVisitedCellItem
UEHistoryInformationFromTheUE ::= CHOICE {
nR NRMobilityHistoryReport,
choice-Extensions ProtocolIE-SingleContainer { {UEHistoryInformationFromTheUE-ExtIEs} }
}
UEHistoryInformationFromTheUE-ExtIEs NGAP-PROTOCOL-IES ::= {
...
}
UEIdentityIndexValue ::= CHOICE {
indexLength10 BIT STRING (SIZE(10)),
choice-Extensions ProtocolIE-SingleContainer { {UEIdentityIndexValue-ExtIEs} }
}
UEIdentityIndexValue-ExtIEs NGAP-PROTOCOL-IES ::= {
...
}
UE-NGAP-IDs ::= CHOICE {
uE-NGAP-ID-pair UE-NGAP-ID-pair,
aMF-UE-NGAP-ID AMF-UE-NGAP-ID,
choice-Extensions ProtocolIE-SingleContainer { {UE-NGAP-IDs-ExtIEs} }
}
UE-NGAP-IDs-ExtIEs NGAP-PROTOCOL-IES ::= {
...
}
UE-NGAP-ID-pair ::= SEQUENCE{
aMF-UE-NGAP-ID AMF-UE-NGAP-ID,
rAN-UE-NGAP-ID RAN-UE-NGAP-ID,
iE-Extensions ProtocolExtensionContainer { {UE-NGAP-ID-pair-ExtIEs} } OPTIONAL,
...
}
UE-NGAP-ID-pair-ExtIEs NGAP-PROTOCOL-EXTENSION ::= {
...
}
UEPagingIdentity ::= CHOICE {
fiveG-S-TMSI FiveG-S-TMSI,
choice-Extensions ProtocolIE-SingleContainer { {UEPagingIdentity-ExtIEs} }
}
UEPagingIdentity-ExtIEs NGAP-PROTOCOL-IES ::= {
...
}
UEPresence ::= ENUMERATED {in, out, unknown, ...}
UEPresenceInAreaOfInterestList ::= SEQUENCE (SIZE(1..maxnoofAoI)) OF UEPresenceInAreaOfInterestItem
UEPresenceInAreaOfInterestItem ::= SEQUENCE {
locationReportingReferenceID LocationReportingReferenceID,
uEPresence UEPresence,
iE-Extensions ProtocolExtensionContainer { {UEPresenceInAreaOfInterestItem-ExtIEs} } OPTIONAL,
...
}
UEPresenceInAreaOfInterestItem-ExtIEs NGAP-PROTOCOL-EXTENSION ::= {
...
}
UERadioCapability ::= OCTET STRING
UERadioCapabilityForPaging ::= SEQUENCE {
uERadioCapabilityForPagingOfNR UERadioCapabilityForPagingOfNR OPTIONAL,
uERadioCapabilityForPagingOfEUTRA UERadioCapabilityForPagingOfEUTRA OPTIONAL,
iE-Extensions ProtocolExtensionContainer { {UERadioCapabilityForPaging-ExtIEs} } OPTIONAL,
...
}
UERadioCapabilityForPaging-ExtIEs NGAP-PROTOCOL-EXTENSION ::= {
{ ID id-UERadioCapabilityForPagingOfNB-IoT CRITICALITY ignore EXTENSION UERadioCapabilityForPagingOfNB-IoT PRESENCE optional },
...
}
UERadioCapabilityForPagingOfNB-IoT ::= OCTET STRING
UERadioCapabilityForPagingOfNR ::= OCTET STRING
UERadioCapabilityForPagingOfEUTRA ::= OCTET STRING
UERadioCapabilityID ::= OCTET STRING
UERetentionInformation ::= ENUMERATED {
ues-retained,
...
}
UERLFReportContainer ::= CHOICE {
nR NRUERLFReportContainer,
lTE LTEUERLFReportContainer,
choice-Extensions ProtocolIE-SingleContainer { {UERLFReportContainer-ExtIEs} }
}
UERLFReportContainer-ExtIEs NGAP-PROTOCOL-IES ::= {
...
}
UESecurityCapabilities ::= SEQUENCE {
nRencryptionAlgorithms NRencryptionAlgorithms,
nRintegrityProtectionAlgorithms NRintegrityProtectionAlgorithms,
eUTRAencryptionAlgorithms EUTRAencryptionAlgorithms,
eUTRAintegrityProtectionAlgorithms EUTRAintegrityProtectionAlgorithms,
iE-Extensions ProtocolExtensionContainer { {UESecurityCapabilities-ExtIEs} } OPTIONAL,
...
}
UESecurityCapabilities-ExtIEs NGAP-PROTOCOL-EXTENSION ::= {
...
}
UESliceMaximumBitRateList ::= SEQUENCE (SIZE(1..maxnoofAllowedS-NSSAIs)) OF UESliceMaximumBitRateItem
UESliceMaximumBitRateItem ::= SEQUENCE {
s-NSSAI S-NSSAI,
uESliceMaximumBitRateDL BitRate,
uESliceMaximumBitRateUL BitRate,
iE-Extensions ProtocolExtensionContainer { { UESliceMaximumBitRateItem-ExtIEs} } OPTIONAL,
...
}
UESliceMaximumBitRateItem-ExtIEs NGAP-PROTOCOL-EXTENSION ::= {
...
}
UE-UP-CIoT-Support ::= ENUMERATED {supported, ...}
UL-CP-SecurityInformation ::= SEQUENCE {
ul-NAS-MAC UL-NAS-MAC,
ul-NAS-Count UL-NAS-Count,
iE-Extensions ProtocolExtensionContainer { { UL-CP-SecurityInformation-ExtIEs} } OPTIONAL,
...
}
UL-CP-SecurityInformation-ExtIEs NGAP-PROTOCOL-EXTENSION ::= {
...
}
UL-NAS-MAC ::= BIT STRING (SIZE (16))
UL-NAS-Count ::= BIT STRING (SIZE (5))
UL-NGU-UP-TNLModifyList ::= SEQUENCE (SIZE(1..maxnoofMultiConnectivity)) OF UL-NGU-UP-TNLModifyItem
UL-NGU-UP-TNLModifyItem ::= SEQUENCE {
uL-NGU-UP-TNLInformation UPTransportLayerInformation,
dL-NGU-UP-TNLInformation UPTransportLayerInformation,
iE-Extensions ProtocolExtensionContainer { {UL-NGU-UP-TNLModifyItem-ExtIEs} } OPTIONAL,
...
}
UL-NGU-UP-TNLModifyItem-ExtIEs NGAP-PROTOCOL-EXTENSION ::= {
{ ID id-RedundantUL-NGU-UP-TNLInformation CRITICALITY ignore EXTENSION UPTransportLayerInformation PRESENCE optional }|
{ ID id-RedundantDL-NGU-UP-TNLInformation CRITICALITY ignore EXTENSION UPTransportLayerInformation PRESENCE optional },
...
}
UnavailableGUAMIList ::= SEQUENCE (SIZE(1..maxnoofServedGUAMIs)) OF UnavailableGUAMIItem
UnavailableGUAMIItem ::= SEQUENCE {
gUAMI GUAMI,
timerApproachForGUAMIRemoval TimerApproachForGUAMIRemoval OPTIONAL,
backupAMFName AMFName OPTIONAL,
iE-Extensions ProtocolExtensionContainer { {UnavailableGUAMIItem-ExtIEs} } OPTIONAL,
...
}
UnavailableGUAMIItem-ExtIEs NGAP-PROTOCOL-EXTENSION ::= {
{ID id-ExtendedBackupAMFName CRITICALITY ignore EXTENSION Extended-AMFName PRESENCE optional},
...
}
ULForwarding ::= ENUMERATED {
ul-forwarding-proposed,
...
}
UpdateFeedback ::= BIT STRING (SIZE(8, ...))
UPTransportLayerInformation ::= CHOICE {
gTPTunnel GTPTunnel,
choice-Extensions ProtocolIE-SingleContainer { {UPTransportLayerInformation-ExtIEs} }
}
UPTransportLayerInformation-ExtIEs NGAP-PROTOCOL-IES ::= {
...
}
UPTransportLayerInformationList ::= SEQUENCE (SIZE(1..maxnoofMultiConnectivityMinusOne)) OF UPTransportLayerInformationItem
UPTransportLayerInformationItem ::= SEQUENCE {
nGU-UP-TNLInformation UPTransportLayerInformation,
iE-Extensions ProtocolExtensionContainer { {UPTransportLayerInformationItem-ExtIEs} } OPTIONAL,
...
}
UPTransportLayerInformationItem-ExtIEs NGAP-PROTOCOL-EXTENSION ::= {
{ ID id-CommonNetworkInstance CRITICALITY ignore EXTENSION CommonNetworkInstance PRESENCE optional },
...
}
UPTransportLayerInformationPairList ::= SEQUENCE (SIZE(1..maxnoofMultiConnectivityMinusOne)) OF UPTransportLayerInformationPairItem
UPTransportLayerInformationPairItem ::= SEQUENCE {
uL-NGU-UP-TNLInformation UPTransportLayerInformation,
dL-NGU-UP-TNLInformation UPTransportLayerInformation,
iE-Extensions ProtocolExtensionContainer { {UPTransportLayerInformationPairItem-ExtIEs} } OPTIONAL,
...
}
UPTransportLayerInformationPairItem-ExtIEs NGAP-PROTOCOL-EXTENSION ::= {
...
}
URI-address ::= VisibleString
UserLocationInformation ::= CHOICE {
userLocationInformationEUTRA UserLocationInformationEUTRA,
userLocationInformationNR UserLocationInformationNR,
userLocationInformationN3IWF-with-PortNumber UserLocationInformationN3IWF-with-PortNumber,
choice-Extensions ProtocolIE-SingleContainer { {UserLocationInformation-ExtIEs} }
}
UserLocationInformation-ExtIEs NGAP-PROTOCOL-IES ::= {
{ ID id-UserLocationInformationTNGF CRITICALITY ignore TYPE UserLocationInformationTNGF PRESENCE mandatory }|
{ ID id-UserLocationInformationTWIF CRITICALITY ignore TYPE UserLocationInformationTWIF PRESENCE mandatory }|
{ ID id-UserLocationInformationW-AGF CRITICALITY ignore TYPE UserLocationInformationW-AGF PRESENCE mandatory }|
{ ID id-UserLocationInformationN3IWF-without-PortNumber CRITICALITY ignore TYPE UserLocationInformationN3IWF-without-PortNumber PRESENCE mandatory },
...
}
UserLocationInformationEUTRA ::= SEQUENCE {
eUTRA-CGI EUTRA-CGI,
tAI TAI,
timeStamp TimeStamp OPTIONAL,
iE-Extensions ProtocolExtensionContainer { {UserLocationInformationEUTRA-ExtIEs} } OPTIONAL,
...
}
UserLocationInformationEUTRA-ExtIEs NGAP-PROTOCOL-EXTENSION ::= {
{ ID id-PSCellInformation CRITICALITY ignore EXTENSION NGRAN-CGI PRESENCE optional},
...
}
UserLocationInformationN3IWF-with-PortNumber ::= SEQUENCE {
iPAddress TransportLayerAddress,
portNumber PortNumber,
iE-Extensions ProtocolExtensionContainer { {UserLocationInformationN3IWF-with-PortNumber-ExtIEs} } OPTIONAL,
...
}
UserLocationInformationN3IWF-with-PortNumber-ExtIEs NGAP-PROTOCOL-EXTENSION ::= {
{ ID id-TAI CRITICALITY ignore EXTENSION TAI PRESENCE optional },
...
}
UserLocationInformationN3IWF-without-PortNumber ::= SEQUENCE {
iPAddress TransportLayerAddress,
tAI TAI OPTIONAL,
iE-Extensions ProtocolExtensionContainer { { UserLocationInformationN3IWF-without-PortNumber-ExtIEs} } OPTIONAL,
...
}
UserLocationInformationN3IWF-without-PortNumber-ExtIEs NGAP-PROTOCOL-EXTENSION ::= {
...
}
UserLocationInformationTNGF ::= SEQUENCE {
tNAP-ID TNAP-ID,
iPAddress TransportLayerAddress,
portNumber PortNumber OPTIONAL,
iE-Extensions ProtocolExtensionContainer { {UserLocationInformationTNGF-ExtIEs} } OPTIONAL,
...
}
UserLocationInformationTNGF-ExtIEs NGAP-PROTOCOL-EXTENSION ::= {
{ ID id-TAI CRITICALITY ignore EXTENSION TAI PRESENCE optional },
...
}
UserLocationInformationTWIF ::= SEQUENCE {
tWAP-ID TWAP-ID,
iPAddress TransportLayerAddress,
portNumber PortNumber OPTIONAL,
iE-Extensions ProtocolExtensionContainer { {UserLocationInformationTWIF-ExtIEs} } OPTIONAL,
...
}
UserLocationInformationTWIF-ExtIEs NGAP-PROTOCOL-EXTENSION ::= {
{ ID id-TAI CRITICALITY ignore EXTENSION TAI PRESENCE optional },
...
}
UserLocationInformationW-AGF ::= CHOICE {
globalLine-ID GlobalLine-ID,
hFCNode-ID HFCNode-ID,
choice-Extensions ProtocolIE-SingleContainer { { UserLocationInformationW-AGF-ExtIEs} }
}
UserLocationInformationW-AGF-ExtIEs NGAP-PROTOCOL-IES ::= {
{ ID id-GlobalCable-ID CRITICALITY ignore TYPE GlobalCable-ID PRESENCE mandatory }|
{ ID id-HFCNode-ID-new CRITICALITY ignore TYPE HFCNode-ID-new PRESENCE mandatory }|
{ ID id-GlobalCable-ID-new CRITICALITY ignore TYPE GlobalCable-ID-new PRESENCE mandatory },
...
}
UserLocationInformationNR ::= SEQUENCE {
nR-CGI NR-CGI,
tAI TAI,
timeStamp TimeStamp OPTIONAL,
iE-Extensions ProtocolExtensionContainer { {UserLocationInformationNR-ExtIEs} } OPTIONAL,
...
}
UserLocationInformationNR-ExtIEs NGAP-PROTOCOL-EXTENSION ::= {
{ ID id-PSCellInformation CRITICALITY ignore EXTENSION NGRAN-CGI PRESENCE optional }|
{ ID id-NID CRITICALITY reject EXTENSION NID PRESENCE optional }|
{ ID id-NRNTNTAIInformation CRITICALITY ignore EXTENSION NRNTNTAIInformation PRESENCE optional }|
{ ID id-MobileIAB-MTUserLocationInformation CRITICALITY ignore EXTENSION MobileIAB-MTUserLocationInformation PRESENCE optional },
...
}
UserPlaneFailureIndication ::= SEQUENCE {
userPlaneFailureType UserPlaneFailureType,
uL-NGU-UP-TNLInformation UPTransportLayerInformation,
dL-NGU-UP-TNLInformation UPTransportLayerInformation,
iE-Extensions ProtocolExtensionContainer { { UserPlaneFailureIndication-ExtIEs} } OPTIONAL,
...
}
UserPlaneFailureIndication-ExtIEs NGAP-PROTOCOL-EXTENSION ::= {
...
}
UserPlaneFailureIndicationReport ::= ENUMERATED {
qos-flows-and-tunnel-to-be-released,
qoS-flows-to-be-moved,
new-transport-address-allocated,
...
}
UserPlaneFailureType ::= ENUMERATED {
gtp-u-error-indication-received,
up-path-failure,
...
}
UserPlaneSecurityInformation ::= SEQUENCE {
securityResult SecurityResult,
securityIndication SecurityIndication,
iE-Extensions ProtocolExtensionContainer { {UserPlaneSecurityInformation-ExtIEs} } OPTIONAL,
...
}
UserPlaneSecurityInformation-ExtIEs NGAP-PROTOCOL-EXTENSION ::= {
...
}
-- V
VolumeTimedReportList ::= SEQUENCE (SIZE(1..maxnoofTimePeriods)) OF VolumeTimedReport-Item
VolumeTimedReport-Item ::= SEQUENCE {
startTimeStamp OCTET STRING (SIZE(4)),
endTimeStamp OCTET STRING (SIZE(4)),
usageCountUL INTEGER (0..18446744073709551615),
usageCountDL INTEGER (0..18446744073709551615),
iE-Extensions ProtocolExtensionContainer { {VolumeTimedReport-Item-ExtIEs} } OPTIONAL,
...
}
VolumeTimedReport-Item-ExtIEs NGAP-PROTOCOL-EXTENSION ::= {
...
}
-- W
W-AGF-ID ::= CHOICE {
w-AGF-ID BIT STRING (SIZE(16, ...)),
choice-Extensions ProtocolIE-SingleContainer { {W-AGF-ID-ExtIEs} }
}
W-AGF-ID-ExtIEs NGAP-PROTOCOL-IES ::= {
...
}
WarningAreaCoordinates ::= OCTET STRING (SIZE(1..1024))
WarningAreaList ::= CHOICE {
eUTRA-CGIListForWarning EUTRA-CGIListForWarning,
nR-CGIListForWarning NR-CGIListForWarning,
tAIListForWarning TAIListForWarning,
emergencyAreaIDList EmergencyAreaIDList,
choice-Extensions ProtocolIE-SingleContainer { {WarningAreaList-ExtIEs} }
}
WarningAreaList-ExtIEs NGAP-PROTOCOL-IES ::= {
...
}
WarningMessageContents ::= OCTET STRING (SIZE(1..9600))
WarningSecurityInfo ::= OCTET STRING (SIZE(50))
WarningType ::= OCTET STRING (SIZE(2))
WLANMeasurementConfiguration ::= SEQUENCE {
wlanMeasConfig WLANMeasConfig,
wlanMeasConfigNameList WLANMeasConfigNameList OPTIONAL,
wlan-rssi ENUMERATED {true, ...} OPTIONAL,
wlan-rtt ENUMERATED {true, ...} OPTIONAL,
iE-Extensions ProtocolExtensionContainer { { WLANMeasurementConfiguration-ExtIEs } } OPTIONAL,
...
}
WLANMeasurementConfiguration-ExtIEs NGAP-PROTOCOL-EXTENSION ::= {
...
}
WLANMeasConfigNameList ::= SEQUENCE (SIZE(1..maxnoofWLANName)) OF WLANMeasConfigNameItem
WLANMeasConfigNameItem ::= SEQUENCE {
wLANName WLANName,
iE-Extensions ProtocolExtensionContainer { { WLANMeasConfigNameItem-ExtIEs } } OPTIONAL,
...
}
WLANMeasConfigNameItem-ExtIEs NGAP-PROTOCOL-EXTENSION ::= {
...
}
WLANMeasConfig::= ENUMERATED {setup,...}
WLANName ::= OCTET STRING (SIZE (1..32))
WUS-Assistance-Information ::= SEQUENCE {
pagingProbabilityInformation PagingProbabilityInformation,
iE-Extensions ProtocolExtensionContainer { { WUS-Assistance-Information-ExtIEs } } OPTIONAL,
...
}
WUS-Assistance-Information-ExtIEs NGAP-PROTOCOL-EXTENSION ::= {
...
}
-- X
XnExtTLAs ::= SEQUENCE (SIZE(1..maxnoofXnExtTLAs)) OF XnExtTLA-Item
XnExtTLA-Item ::= SEQUENCE {
iPsecTLA TransportLayerAddress OPTIONAL,
gTP-TLAs XnGTP-TLAs OPTIONAL,
iE-Extensions ProtocolExtensionContainer { {XnExtTLA-Item-ExtIEs} } OPTIONAL,
...
}
XnExtTLA-Item-ExtIEs NGAP-PROTOCOL-EXTENSION ::= {
{ ID id-SCTP-TLAs CRITICALITY ignore EXTENSION SCTP-TLAs PRESENCE optional },
...
}
XnGTP-TLAs ::= SEQUENCE (SIZE(1..maxnoofXnGTP-TLAs)) OF TransportLayerAddress
XnTLAs ::= SEQUENCE (SIZE(1..maxnoofXnTLAs)) OF TransportLayerAddress
XnTNLConfigurationInfo ::= SEQUENCE {
xnTransportLayerAddresses XnTLAs,
xnExtendedTransportLayerAddresses XnExtTLAs OPTIONAL,
iE-Extensions ProtocolExtensionContainer { {XnTNLConfigurationInfo-ExtIEs} } OPTIONAL,
...
}
XnTNLConfigurationInfo-ExtIEs NGAP-PROTOCOL-EXTENSION ::= {
...
}
XrDeviceWith2Rx ::= ENUMERATED {true, ...}
-- Y
-- Z
END

-- **************************************************************
--
-- Common definitions
--
-- **************************************************************
NGAP-CommonDataTypes {
itu-t (0) identified-organization (4) etsi (0) mobileDomain (0)
ngran-Access (22) modules (3) ngap (1) version1 (1) ngap-CommonDataTypes (3) }
DEFINITIONS AUTOMATIC TAGS ::=
BEGIN
Criticality ::= ENUMERATED { reject, ignore, notify }
Presence ::= ENUMERATED { optional, conditional, mandatory }
PrivateIE-ID ::= CHOICE {
local INTEGER (0..65535),
global OBJECT IDENTIFIER
}
ProcedureCode ::= INTEGER (0..255)
ProtocolExtensionID ::= INTEGER (0..65535)
ProtocolIE-ID ::= INTEGER (0..65535)
TriggeringMessage ::= ENUMERATED { initiating-message, successful-outcome, unsuccessful-outcome }
END

-- **************************************************************
--
-- Constant definitions
--
-- **************************************************************
NGAP-Constants {
itu-t (0) identified-organization (4) etsi (0) mobileDomain (0)
ngran-Access (22) modules (3) ngap (1) version1 (1) ngap-Constants (4) }
DEFINITIONS AUTOMATIC TAGS ::=
BEGIN
-- **************************************************************
--
-- IE parameter types from other modules.
--
-- **************************************************************
IMPORTS
ProcedureCode,
ProtocolIE-ID
FROM NGAP-CommonDataTypes;
-- **************************************************************
--
-- Elementary Procedures
--
-- **************************************************************
id-AMFConfigurationUpdate ProcedureCode ::= 0
id-AMFStatusIndication ProcedureCode ::= 1
id-CellTrafficTrace ProcedureCode ::= 2
id-DeactivateTrace ProcedureCode ::= 3
id-DownlinkNASTransport ProcedureCode ::= 4
id-DownlinkNonUEAssociatedNRPPaTransport ProcedureCode ::= 5
id-DownlinkRANConfigurationTransfer ProcedureCode ::= 6
id-DownlinkRANStatusTransfer ProcedureCode ::= 7
id-DownlinkUEAssociatedNRPPaTransport ProcedureCode ::= 8
id-ErrorIndication ProcedureCode ::= 9
id-HandoverCancel ProcedureCode ::= 10
id-HandoverNotification ProcedureCode ::= 11
id-HandoverPreparation ProcedureCode ::= 12
id-HandoverResourceAllocation ProcedureCode ::= 13
id-InitialContextSetup ProcedureCode ::= 14
id-InitialUEMessage ProcedureCode ::= 15
id-LocationReportingControl ProcedureCode ::= 16
id-LocationReportingFailureIndication ProcedureCode ::= 17
id-LocationReport ProcedureCode ::= 18
id-NASNonDeliveryIndication ProcedureCode ::= 19
id-NGReset ProcedureCode ::= 20
id-NGSetup ProcedureCode ::= 21
id-OverloadStart ProcedureCode ::= 22
id-OverloadStop ProcedureCode ::= 23
id-Paging ProcedureCode ::= 24
id-PathSwitchRequest ProcedureCode ::= 25
id-PDUSessionResourceModify ProcedureCode ::= 26
id-PDUSessionResourceModifyIndication ProcedureCode ::= 27
id-PDUSessionResourceRelease ProcedureCode ::= 28
id-PDUSessionResourceSetup ProcedureCode ::= 29
id-PDUSessionResourceNotify ProcedureCode ::= 30
id-PrivateMessage ProcedureCode ::= 31
id-PWSCancel ProcedureCode ::= 32
id-PWSFailureIndication ProcedureCode ::= 33
id-PWSRestartIndication ProcedureCode ::= 34
id-RANConfigurationUpdate ProcedureCode ::= 35
id-RerouteNASRequest ProcedureCode ::= 36
id-RRCInactiveTransitionReport ProcedureCode ::= 37
id-TraceFailureIndication ProcedureCode ::= 38
id-TraceStart ProcedureCode ::= 39
id-UEContextModification ProcedureCode ::= 40
id-UEContextRelease ProcedureCode ::= 41
id-UEContextReleaseRequest ProcedureCode ::= 42
id-UERadioCapabilityCheck ProcedureCode ::= 43
id-UERadioCapabilityInfoIndication ProcedureCode ::= 44
id-UETNLABindingRelease ProcedureCode ::= 45
id-UplinkNASTransport ProcedureCode ::= 46
id-UplinkNonUEAssociatedNRPPaTransport ProcedureCode ::= 47
id-UplinkRANConfigurationTransfer ProcedureCode ::= 48
id-UplinkRANStatusTransfer ProcedureCode ::= 49
id-UplinkUEAssociatedNRPPaTransport ProcedureCode ::= 50
id-WriteReplaceWarning ProcedureCode ::= 51
id-SecondaryRATDataUsageReport ProcedureCode ::= 52
id-UplinkRIMInformationTransfer ProcedureCode ::= 53
id-DownlinkRIMInformationTransfer ProcedureCode ::= 54
id-RetrieveUEInformation ProcedureCode ::= 55
id-UEInformationTransfer ProcedureCode ::= 56
id-RANCPRelocationIndication ProcedureCode ::= 57
id-UEContextResume ProcedureCode ::= 58
id-UEContextSuspend ProcedureCode ::= 59
id-UERadioCapabilityIDMapping ProcedureCode ::= 60
id-HandoverSuccess ProcedureCode ::= 61
id-UplinkRANEarlyStatusTransfer ProcedureCode ::= 62
id-DownlinkRANEarlyStatusTransfer ProcedureCode ::= 63
id-AMFCPRelocationIndication ProcedureCode ::= 64
id-ConnectionEstablishmentIndication ProcedureCode ::= 65
id-BroadcastSessionModification ProcedureCode ::= 66
id-BroadcastSessionRelease ProcedureCode ::= 67
id-BroadcastSessionSetup ProcedureCode ::= 68
id-DistributionSetup ProcedureCode ::= 69
id-DistributionRelease ProcedureCode ::= 70
id-MulticastSessionActivation ProcedureCode ::= 71
id-MulticastSessionDeactivation ProcedureCode ::= 72
id-MulticastSessionUpdate ProcedureCode ::= 73
id-MulticastGroupPaging ProcedureCode ::= 74
id-BroadcastSessionReleaseRequired ProcedureCode ::= 75
id-TimingSynchronisationStatus ProcedureCode ::= 76
id-TimingSynchronisationStatusReport ProcedureCode ::= 77
id-MTCommunicationHandling ProcedureCode ::= 78
id-RANPagingRequest ProcedureCode ::= 79
id-BroadcastSessionTransport ProcedureCode ::= 80
-- **************************************************************
--
-- Extension constants
--
-- **************************************************************
maxPrivateIEs INTEGER ::= 65535
maxProtocolExtensions INTEGER ::= 65535
maxProtocolIEs INTEGER ::= 65535
-- **************************************************************
--
-- Lists
--
-- **************************************************************
maxnoofAllowedAreas INTEGER ::= 16
maxnoofAllowedCAGsperPLMN INTEGER ::= 256
maxnoofAllowedS-NSSAIs INTEGER ::= 8
maxnoofBluetoothName INTEGER ::= 4
maxnoofBPLMNs INTEGER ::= 12
maxnoofCAGSperCell INTEGER ::= 64
maxnoofCellIDforMDT INTEGER ::= 32
maxnoofCellIDforWarning INTEGER ::= 65535
maxnoofCellinAoI INTEGER ::= 256
maxnoofCellinEAI INTEGER ::= 65535
maxnoofCellinTAI INTEGER ::= 65535
maxnoofCellsforMBS INTEGER ::= 8192
maxnoofCellsingNB INTEGER ::= 16384
maxnoofCellsinngeNB INTEGER ::= 256
maxnoofCellsinNGRANNode INTEGER ::= 16384
maxnoofCellsinUEHistoryInfo INTEGER ::= 16
maxnoofCellsUEMovingTrajectory INTEGER ::= 16
maxnoofDRBs INTEGER ::= 32
maxnoofEmergencyAreaID INTEGER ::= 65535
maxnoofEAIforRestart INTEGER ::= 256
maxnoofEPLMNs INTEGER ::= 15
maxnoofEPLMNsPlusOne INTEGER ::= 16
maxnoofE-RABs INTEGER ::= 256
maxnoofErrors INTEGER ::= 256
maxnoofExtSliceItems INTEGER ::= 65535
maxnoofForbTACs INTEGER ::= 4096
maxnoofFreqforMDT INTEGER ::= 8
maxnoofMBSAreaSessionIDs INTEGER ::= 256
maxnoofMBSFSAs INTEGER ::= 64
maxnoofMBSQoSFlows INTEGER ::= 64
maxnoofMBSSessions INTEGER ::= 32
maxnoofMBSSessionsofUE INTEGER ::= 256
maxnoofMBSServiceAreaInformation INTEGER ::= 256
maxnoofMDTPLMNs INTEGER ::= 16
maxnoofMRBs INTEGER ::= 32
maxnoofMultiConnectivity INTEGER ::= 4
maxnoofMultiConnectivityMinusOne INTEGER ::= 3
maxnoofNeighPCIforMDT INTEGER ::= 32
maxnoofNGAPIESupportInfo INTEGER ::= 32
maxnoofNGConnectionsToReset INTEGER ::= 65536
maxnoofNRCellBands INTEGER ::= 32
maxnoofNSAGs INTEGER ::= 256
maxnoofPagingAreas INTEGER ::= 64
maxnoofPC5QoSFlows INTEGER ::= 2048
maxnoofPDUSessions INTEGER ::= 256
maxnoofPLMNs INTEGER ::= 12
maxnoofPSCellsPerPrimaryCellinUEHistoryInfo INTEGER ::= 8
maxnoofQosFlows INTEGER ::= 64
maxnoofQosParaSets INTEGER ::= 8
maxnoofRANNodeinAoI INTEGER ::= 64
maxnoofRecommendedCells INTEGER ::= 16
maxnoofRecommendedRANNodes INTEGER ::= 16
maxnoofAoI INTEGER ::= 64
maxnoofAoIMinusOne INTEGER ::= 63
maxnoofReportedCells INTEGER ::= 256
maxnoofSensorName INTEGER ::= 3
maxnoofServedGUAMIs INTEGER ::= 256
maxnoofSliceItems INTEGER ::= 1024
maxnoofSuccessfulHOReports INTEGER ::= 64
maxnoofTACs INTEGER ::= 256
maxnoofTACsinNTN INTEGER ::= 12
maxnoofTAforMDT INTEGER ::= 8
maxnoofTAIforInactive INTEGER ::= 16
maxnoofSupportedTAIforMBS INTEGER ::= 256
maxnoofTAIforMBS INTEGER ::= 1024
maxnoofTAIforPaging INTEGER ::= 16
maxnoofTAIforRestart INTEGER ::= 2048
maxnoofTAIforWarning INTEGER ::= 65535
maxnoofTAIinAoI INTEGER ::= 16
maxnoofTimePeriods INTEGER ::= 2
maxnoofTNLAssociations INTEGER ::= 32
maxnoofUEsforPaging INTEGER ::= 4096
maxnoofUETypes INTEGER ::= 8
maxnoofWLANName INTEGER ::= 4
maxnoofXnExtTLAs INTEGER ::= 16
maxnoofXnGTP-TLAs INTEGER ::= 16
maxnoofXnTLAs INTEGER ::= 2
maxnoofCandidateCells INTEGER ::= 32
maxnoofTargetS-NSSAIs INTEGER ::= 8
maxNRARFCN INTEGER ::= 3279165
maxnoofCellIDforQMC INTEGER ::= 32
maxnoofPLMNforQMC INTEGER ::= 16
maxnoofUEAppLayerMeas INTEGER ::= 16
maxnoofSNSSAIforQMC INTEGER ::= 16
maxnoofTAforQMC INTEGER ::= 8
maxnoofThresholdsForExcessPacketDelay INTEGER ::= 255
maxnoofESNPNs INTEGER ::= 15
maxnoofCandidateRelayUEs INTEGER ::= 32
maxnoofSuccessfulPSCellChangeReports INTEGER ::= 64
maxnoofCellsTSS INTEGER ::= 16384
maxnoofPeriodicities INTEGER ::= 8
maxnoofCAGforMDT INTEGER ::= 256
maxnoofMDTSNPNs INTEGER ::= 16
maxnoofPartiallyAllowedS-NSSAIs INTEGER ::= 8
maxnoofRSPPQoSFlows INTEGER ::= 2048
-- **************************************************************
--
-- IEs
--
-- **************************************************************
id-AllowedNSSAI ProtocolIE-ID ::= 0
id-AMFName ProtocolIE-ID ::= 1
id-AMFOverloadResponse ProtocolIE-ID ::= 2
id-AMFSetID ProtocolIE-ID ::= 3
id-AMF-TNLAssociationFailedToSetupList ProtocolIE-ID ::= 4
id-AMF-TNLAssociationSetupList ProtocolIE-ID ::= 5
id-AMF-TNLAssociationToAddList ProtocolIE-ID ::= 6
id-AMF-TNLAssociationToRemoveList ProtocolIE-ID ::= 7
id-AMF-TNLAssociationToUpdateList ProtocolIE-ID ::= 8
id-AMFTrafficLoadReductionIndication ProtocolIE-ID ::= 9
id-AMF-UE-NGAP-ID ProtocolIE-ID ::= 10
id-AssistanceDataForPaging ProtocolIE-ID ::= 11
id-BroadcastCancelledAreaList ProtocolIE-ID ::= 12
id-BroadcastCompletedAreaList ProtocolIE-ID ::= 13
id-CancelAllWarningMessages ProtocolIE-ID ::= 14
id-Cause ProtocolIE-ID ::= 15
id-CellIDListForRestart ProtocolIE-ID ::= 16
id-ConcurrentWarningMessageInd ProtocolIE-ID ::= 17
id-CoreNetworkAssistanceInformationForInactive ProtocolIE-ID ::= 18
id-CriticalityDiagnostics ProtocolIE-ID ::= 19
id-DataCodingScheme ProtocolIE-ID ::= 20
id-DefaultPagingDRX ProtocolIE-ID ::= 21
id-DirectForwardingPathAvailability ProtocolIE-ID ::= 22
id-EmergencyAreaIDListForRestart ProtocolIE-ID ::= 23
id-EmergencyFallbackIndicator ProtocolIE-ID ::= 24
id-EUTRA-CGI ProtocolIE-ID ::= 25
id-FiveG-S-TMSI ProtocolIE-ID ::= 26
id-GlobalRANNodeID ProtocolIE-ID ::= 27
id-GUAMI ProtocolIE-ID ::= 28
id-HandoverType ProtocolIE-ID ::= 29
id-IMSVoiceSupportIndicator ProtocolIE-ID ::= 30
id-IndexToRFSP ProtocolIE-ID ::= 31
id-InfoOnRecommendedCellsAndRANNodesForPaging ProtocolIE-ID ::= 32
id-LocationReportingRequestType ProtocolIE-ID ::= 33
id-MaskedIMEISV ProtocolIE-ID ::= 34
id-MessageIdentifier ProtocolIE-ID ::= 35
id-MobilityRestrictionList ProtocolIE-ID ::= 36
id-NASC ProtocolIE-ID ::= 37
id-NAS-PDU ProtocolIE-ID ::= 38
id-NASSecurityParametersFromNGRAN ProtocolIE-ID ::= 39
id-NewAMF-UE-NGAP-ID ProtocolIE-ID ::= 40
id-NewSecurityContextInd ProtocolIE-ID ::= 41
id-NGAP-Message ProtocolIE-ID ::= 42
id-NGRAN-CGI ProtocolIE-ID ::= 43
id-NGRANTraceID ProtocolIE-ID ::= 44
id-NR-CGI ProtocolIE-ID ::= 45
id-NRPPa-PDU ProtocolIE-ID ::= 46
id-NumberOfBroadcastsRequested ProtocolIE-ID ::= 47
id-OldAMF ProtocolIE-ID ::= 48
id-OverloadStartNSSAIList ProtocolIE-ID ::= 49
id-PagingDRX ProtocolIE-ID ::= 50
id-PagingOrigin ProtocolIE-ID ::= 51
id-PagingPriority ProtocolIE-ID ::= 52
id-PDUSessionResourceAdmittedList ProtocolIE-ID ::= 53
id-PDUSessionResourceFailedToModifyListModRes ProtocolIE-ID ::= 54
id-PDUSessionResourceFailedToSetupListCxtRes ProtocolIE-ID ::= 55
id-PDUSessionResourceFailedToSetupListHOAck ProtocolIE-ID ::= 56
id-PDUSessionResourceFailedToSetupListPSReq ProtocolIE-ID ::= 57
id-PDUSessionResourceFailedToSetupListSURes ProtocolIE-ID ::= 58
id-PDUSessionResourceHandoverList ProtocolIE-ID ::= 59
id-PDUSessionResourceListCxtRelCpl ProtocolIE-ID ::= 60
id-PDUSessionResourceListHORqd ProtocolIE-ID ::= 61
id-PDUSessionResourceModifyListModCfm ProtocolIE-ID ::= 62
id-PDUSessionResourceModifyListModInd ProtocolIE-ID ::= 63
id-PDUSessionResourceModifyListModReq ProtocolIE-ID ::= 64
id-PDUSessionResourceModifyListModRes ProtocolIE-ID ::= 65
id-PDUSessionResourceNotifyList ProtocolIE-ID ::= 66
id-PDUSessionResourceReleasedListNot ProtocolIE-ID ::= 67
id-PDUSessionResourceReleasedListPSAck ProtocolIE-ID ::= 68
id-PDUSessionResourceReleasedListPSFail ProtocolIE-ID ::= 69
id-PDUSessionResourceReleasedListRelRes ProtocolIE-ID ::= 70
id-PDUSessionResourceSetupListCxtReq ProtocolIE-ID ::= 71
id-PDUSessionResourceSetupListCxtRes ProtocolIE-ID ::= 72
id-PDUSessionResourceSetupListHOReq ProtocolIE-ID ::= 73
id-PDUSessionResourceSetupListSUReq ProtocolIE-ID ::= 74
id-PDUSessionResourceSetupListSURes ProtocolIE-ID ::= 75
id-PDUSessionResourceToBeSwitchedDLList ProtocolIE-ID ::= 76
id-PDUSessionResourceSwitchedList ProtocolIE-ID ::= 77
id-PDUSessionResourceToReleaseListHOCmd ProtocolIE-ID ::= 78
id-PDUSessionResourceToReleaseListRelCmd ProtocolIE-ID ::= 79
id-PLMNSupportList ProtocolIE-ID ::= 80
id-PWSFailedCellIDList ProtocolIE-ID ::= 81
id-RANNodeName ProtocolIE-ID ::= 82
id-RANPagingPriority ProtocolIE-ID ::= 83
id-RANStatusTransfer-TransparentContainer ProtocolIE-ID ::= 84
id-RAN-UE-NGAP-ID ProtocolIE-ID ::= 85
id-RelativeAMFCapacity ProtocolIE-ID ::= 86
id-RepetitionPeriod ProtocolIE-ID ::= 87
id-ResetType ProtocolIE-ID ::= 88
id-RoutingID ProtocolIE-ID ::= 89
id-RRCEstablishmentCause ProtocolIE-ID ::= 90
id-RRCInactiveTransitionReportRequest ProtocolIE-ID ::= 91
id-RRCState ProtocolIE-ID ::= 92
id-SecurityContext ProtocolIE-ID ::= 93
id-SecurityKey ProtocolIE-ID ::= 94
id-SerialNumber ProtocolIE-ID ::= 95
id-ServedGUAMIList ProtocolIE-ID ::= 96
id-SliceSupportList ProtocolIE-ID ::= 97
id-SONConfigurationTransferDL ProtocolIE-ID ::= 98
id-SONConfigurationTransferUL ProtocolIE-ID ::= 99
id-SourceAMF-UE-NGAP-ID ProtocolIE-ID ::= 100
id-SourceToTarget-TransparentContainer ProtocolIE-ID ::= 101
id-SupportedTAList ProtocolIE-ID ::= 102
id-TAIListForPaging ProtocolIE-ID ::= 103
id-TAIListForRestart ProtocolIE-ID ::= 104
id-TargetID ProtocolIE-ID ::= 105
id-TargetToSource-TransparentContainer ProtocolIE-ID ::= 106
id-TimeToWait ProtocolIE-ID ::= 107
id-TraceActivation ProtocolIE-ID ::= 108
id-TraceCollectionEntityIPAddress ProtocolIE-ID ::= 109
id-UEAggregateMaximumBitRate ProtocolIE-ID ::= 110
id-UE-associatedLogicalNG-connectionList ProtocolIE-ID ::= 111
id-UEContextRequest ProtocolIE-ID ::= 112
id-UE-NGAP-IDs ProtocolIE-ID ::= 114
id-UEPagingIdentity ProtocolIE-ID ::= 115
id-UEPresenceInAreaOfInterestList ProtocolIE-ID ::= 116
id-UERadioCapability ProtocolIE-ID ::= 117
id-UERadioCapabilityForPaging ProtocolIE-ID ::= 118
id-UESecurityCapabilities ProtocolIE-ID ::= 119
id-UnavailableGUAMIList ProtocolIE-ID ::= 120
id-UserLocationInformation ProtocolIE-ID ::= 121
id-WarningAreaList ProtocolIE-ID ::= 122
id-WarningMessageContents ProtocolIE-ID ::= 123
id-WarningSecurityInfo ProtocolIE-ID ::= 124
id-WarningType ProtocolIE-ID ::= 125
id-AdditionalUL-NGU-UP-TNLInformation ProtocolIE-ID ::= 126
id-DataForwardingNotPossible ProtocolIE-ID ::= 127
id-DL-NGU-UP-TNLInformation ProtocolIE-ID ::= 128
id-NetworkInstance ProtocolIE-ID ::= 129
id-PDUSessionAggregateMaximumBitRate ProtocolIE-ID ::= 130
id-PDUSessionResourceFailedToModifyListModCfm ProtocolIE-ID ::= 131
id-PDUSessionResourceFailedToSetupListCxtFail ProtocolIE-ID ::= 132
id-PDUSessionResourceListCxtRelReq ProtocolIE-ID ::= 133
id-PDUSessionType ProtocolIE-ID ::= 134
id-QosFlowAddOrModifyRequestList ProtocolIE-ID ::= 135
id-QosFlowSetupRequestList ProtocolIE-ID ::= 136
id-QosFlowToReleaseList ProtocolIE-ID ::= 137
id-SecurityIndication ProtocolIE-ID ::= 138
id-UL-NGU-UP-TNLInformation ProtocolIE-ID ::= 139
id-UL-NGU-UP-TNLModifyList ProtocolIE-ID ::= 140
id-WarningAreaCoordinates ProtocolIE-ID ::= 141
id-PDUSessionResourceSecondaryRATUsageList ProtocolIE-ID ::= 142
id-HandoverFlag ProtocolIE-ID ::= 143
id-SecondaryRATUsageInformation ProtocolIE-ID ::= 144
id-PDUSessionResourceReleaseResponseTransfer ProtocolIE-ID ::= 145
id-RedirectionVoiceFallback ProtocolIE-ID ::= 146
id-UERetentionInformation ProtocolIE-ID ::= 147
id-S-NSSAI ProtocolIE-ID ::= 148
id-PSCellInformation ProtocolIE-ID ::= 149
id-LastEUTRAN-PLMNIdentity ProtocolIE-ID ::= 150
id-MaximumIntegrityProtectedDataRate-DL ProtocolIE-ID ::= 151
id-AdditionalDLForwardingUPTNLInformation ProtocolIE-ID ::= 152
id-AdditionalDLUPTNLInformationForHOList ProtocolIE-ID ::= 153
id-AdditionalNGU-UP-TNLInformation ProtocolIE-ID ::= 154
id-AdditionalDLQosFlowPerTNLInformation ProtocolIE-ID ::= 155
id-SecurityResult ProtocolIE-ID ::= 156
id-ENDC-SONConfigurationTransferDL ProtocolIE-ID ::= 157
id-ENDC-SONConfigurationTransferUL ProtocolIE-ID ::= 158
id-OldAssociatedQosFlowList-ULendmarkerexpected ProtocolIE-ID ::= 159
id-CNTypeRestrictionsForEquivalent ProtocolIE-ID ::= 160
id-CNTypeRestrictionsForServing ProtocolIE-ID ::= 161
id-NewGUAMI ProtocolIE-ID ::= 162
id-ULForwarding ProtocolIE-ID ::= 163
id-ULForwardingUP-TNLInformation ProtocolIE-ID ::= 164
id-CNAssistedRANTuning ProtocolIE-ID ::= 165
id-CommonNetworkInstance ProtocolIE-ID ::= 166
id-NGRAN-TNLAssociationToRemoveList ProtocolIE-ID ::= 167
id-TNLAssociationTransportLayerAddressNGRAN ProtocolIE-ID ::= 168
id-EndpointIPAddressAndPort ProtocolIE-ID ::= 169
id-LocationReportingAdditionalInfo ProtocolIE-ID ::= 170
id-SourceToTarget-AMFInformationReroute ProtocolIE-ID ::= 171
id-AdditionalULForwardingUPTNLInformation ProtocolIE-ID ::= 172
id-SCTP-TLAs ProtocolIE-ID ::= 173
id-SelectedPLMNIdentity ProtocolIE-ID ::= 174
id-RIMInformationTransfer ProtocolIE-ID ::= 175
id-GUAMIType ProtocolIE-ID ::= 176
id-SRVCCOperationPossible ProtocolIE-ID ::= 177
id-TargetRNC-ID ProtocolIE-ID ::= 178
id-RAT-Information ProtocolIE-ID ::= 179
id-ExtendedRATRestrictionInformation ProtocolIE-ID ::= 180
id-QosMonitoringRequest ProtocolIE-ID ::= 181
id-SgNB-UE-X2AP-ID ProtocolIE-ID ::= 182
id-AdditionalRedundantDL-NGU-UP-TNLInformation ProtocolIE-ID ::= 183
id-AdditionalRedundantDLQosFlowPerTNLInformation ProtocolIE-ID ::= 184
id-AdditionalRedundantNGU-UP-TNLInformation ProtocolIE-ID ::= 185
id-AdditionalRedundantUL-NGU-UP-TNLInformation ProtocolIE-ID ::= 186
id-CNPacketDelayBudgetDL ProtocolIE-ID ::= 187
id-CNPacketDelayBudgetUL ProtocolIE-ID ::= 188
id-ExtendedPacketDelayBudget ProtocolIE-ID ::= 189
id-RedundantCommonNetworkInstance ProtocolIE-ID ::= 190
id-RedundantDL-NGU-TNLInformationReused ProtocolIE-ID ::= 191
id-RedundantDL-NGU-UP-TNLInformation ProtocolIE-ID ::= 192
id-RedundantDLQosFlowPerTNLInformation ProtocolIE-ID ::= 193
id-RedundantQosFlowIndicator ProtocolIE-ID ::= 194
id-RedundantUL-NGU-UP-TNLInformation ProtocolIE-ID ::= 195
id-TSCTrafficCharacteristics ProtocolIE-ID ::= 196
id-RedundantPDUSessionInformation ProtocolIE-ID ::= 197
id-UsedRSNInformation ProtocolIE-ID ::= 198
id-IAB-Authorized ProtocolIE-ID ::= 199
id-IAB-Supported ProtocolIE-ID ::= 200
id-IABNodeIndication ProtocolIE-ID ::= 201
id-NB-IoT-PagingDRX ProtocolIE-ID ::= 202
id-NB-IoT-Paging-eDRXInfo ProtocolIE-ID ::= 203
id-NB-IoT-DefaultPagingDRX ProtocolIE-ID ::= 204
id-Enhanced-CoverageRestriction ProtocolIE-ID ::= 205
id-Extended-ConnectedTime ProtocolIE-ID ::= 206
id-PagingAssisDataforCEcapabUE ProtocolIE-ID ::= 207
id-WUS-Assistance-Information ProtocolIE-ID ::= 208
id-UE-DifferentiationInfo ProtocolIE-ID ::= 209
id-NB-IoT-UEPriority ProtocolIE-ID ::= 210
id-UL-CP-SecurityInformation ProtocolIE-ID ::= 211
id-DL-CP-SecurityInformation ProtocolIE-ID ::= 212
id-TAI ProtocolIE-ID ::= 213
id-UERadioCapabilityForPagingOfNB-IoT ProtocolIE-ID ::= 214
id-LTEV2XServicesAuthorized ProtocolIE-ID ::= 215
id-NRV2XServicesAuthorized ProtocolIE-ID ::= 216
id-LTEUESidelinkAggregateMaximumBitrate ProtocolIE-ID ::= 217
id-NRUESidelinkAggregateMaximumBitrate ProtocolIE-ID ::= 218
id-PC5QoSParameters ProtocolIE-ID ::= 219
id-AlternativeQoSParaSetList ProtocolIE-ID ::= 220
id-CurrentQoSParaSetIndex ProtocolIE-ID ::= 221
id-CEmodeBrestricted ProtocolIE-ID ::= 222
id-EUTRA-PagingeDRXInformation ProtocolIE-ID ::= 223
id-CEmodeBSupport-Indicator ProtocolIE-ID ::= 224
id-LTEM-Indication ProtocolIE-ID ::= 225
id-EndIndication ProtocolIE-ID ::= 226
id-EDT-Session ProtocolIE-ID ::= 227
id-UECapabilityInfoRequest ProtocolIE-ID ::= 228
id-PDUSessionResourceFailedToResumeListRESReq ProtocolIE-ID ::= 229
id-PDUSessionResourceFailedToResumeListRESRes ProtocolIE-ID ::= 230
id-PDUSessionResourceSuspendListSUSReq ProtocolIE-ID ::= 231
id-PDUSessionResourceResumeListRESReq ProtocolIE-ID ::= 232
id-PDUSessionResourceResumeListRESRes ProtocolIE-ID ::= 233
id-UE-UP-CIoT-Support ProtocolIE-ID ::= 234
id-Suspend-Request-Indication ProtocolIE-ID ::= 235
id-Suspend-Response-Indication ProtocolIE-ID ::= 236
id-RRC-Resume-Cause ProtocolIE-ID ::= 237
id-RGLevelWirelineAccessCharacteristics ProtocolIE-ID ::= 238
id-W-AGFIdentityInformation ProtocolIE-ID ::= 239
id-GlobalTNGF-ID ProtocolIE-ID ::= 240
id-GlobalTWIF-ID ProtocolIE-ID ::= 241
id-GlobalW-AGF-ID ProtocolIE-ID ::= 242
id-UserLocationInformationW-AGF ProtocolIE-ID ::= 243
id-UserLocationInformationTNGF ProtocolIE-ID ::= 244
id-AuthenticatedIndication ProtocolIE-ID ::= 245
id-TNGFIdentityInformation ProtocolIE-ID ::= 246
id-TWIFIdentityInformation ProtocolIE-ID ::= 247
id-UserLocationInformationTWIF ProtocolIE-ID ::= 248
id-DataForwardingResponseERABList ProtocolIE-ID ::= 249
id-IntersystemSONConfigurationTransferDL ProtocolIE-ID ::= 250
id-IntersystemSONConfigurationTransferUL ProtocolIE-ID ::= 251
id-SONInformationReport ProtocolIE-ID ::= 252
id-UEHistoryInformationFromTheUE ProtocolIE-ID ::= 253
id-ManagementBasedMDTPLMNList ProtocolIE-ID ::= 254
id-MDTConfiguration ProtocolIE-ID ::= 255
id-PrivacyIndicator ProtocolIE-ID ::= 256
id-TraceCollectionEntityURI ProtocolIE-ID ::= 257
id-NPN-Support ProtocolIE-ID ::= 258
id-NPN-AccessInformation ProtocolIE-ID ::= 259
id-NPN-PagingAssistanceInformation ProtocolIE-ID ::= 260
id-NPN-MobilityInformation ProtocolIE-ID ::= 261
id-TargettoSource-Failure-TransparentContainer ProtocolIE-ID ::= 262
id-NID ProtocolIE-ID ::= 263
id-UERadioCapabilityID ProtocolIE-ID ::= 264
id-UERadioCapability-EUTRA-Format ProtocolIE-ID ::= 265
id-DAPSRequestInfo ProtocolIE-ID ::= 266
id-DAPSResponseInfoList ProtocolIE-ID ::= 267
id-EarlyStatusTransfer-TransparentContainer ProtocolIE-ID ::= 268
id-NotifySourceNGRANNode ProtocolIE-ID ::= 269
id-ExtendedSliceSupportList ProtocolIE-ID ::= 270
id-ExtendedTAISliceSupportList ProtocolIE-ID ::= 271
id-ConfiguredTACIndication ProtocolIE-ID ::= 272
id-Extended-RANNodeName ProtocolIE-ID ::= 273
id-Extended-AMFName ProtocolIE-ID ::= 274
id-GlobalCable-ID ProtocolIE-ID ::= 275
id-QosMonitoringReportingFrequency ProtocolIE-ID ::= 276
id-QosFlowParametersList ProtocolIE-ID ::= 277
id-QosFlowFeedbackList ProtocolIE-ID ::= 278
id-BurstArrivalTimeDownlink ProtocolIE-ID ::= 279
id-ExtendedUEIdentityIndexValue ProtocolIE-ID ::= 280
id-PduSessionExpectedUEActivityBehaviour ProtocolIE-ID ::= 281
id-MicoAllPLMN ProtocolIE-ID ::= 282
id-QosFlowFailedToSetupList ProtocolIE-ID ::= 283
id-SourceTNLAddrInfo ProtocolIE-ID ::= 284
id-ExtendedReportIntervalMDT ProtocolIE-ID ::= 285
id-SourceNodeID ProtocolIE-ID ::= 286
id-NRNTNTAIInformation ProtocolIE-ID ::= 287
id-UEContextReferenceAtSource ProtocolIE-ID ::= 288
id-LastVisitedPSCellList ProtocolIE-ID ::= 289
id-IntersystemSONInformationRequest ProtocolIE-ID ::= 290
id-IntersystemSONInformationReply ProtocolIE-ID ::= 291
id-EnergySavingIndication ProtocolIE-ID ::= 292
id-IntersystemResourceStatusUpdate ProtocolIE-ID ::= 293
id-SuccessfulHandoverReportList ProtocolIE-ID ::= 294
id-MBS-AreaSessionID ProtocolIE-ID ::= 295
id-MBS-QoSFlowsToBeSetupList ProtocolIE-ID ::= 296
id-MBS-QoSFlowsToBeSetupModList ProtocolIE-ID ::= 297
id-MBS-ServiceArea ProtocolIE-ID ::= 298
id-MBS-SessionID ProtocolIE-ID ::= 299
id-MBS-DistributionReleaseRequestTransfer ProtocolIE-ID ::= 300
id-MBS-DistributionSetupRequestTransfer ProtocolIE-ID ::= 301
id-MBS-DistributionSetupResponseTransfer ProtocolIE-ID ::= 302
id-MBS-DistributionSetupUnsuccessfulTransfer ProtocolIE-ID ::= 303
id-MulticastSessionActivationRequestTransfer ProtocolIE-ID ::= 304
id-MulticastSessionDeactivationRequestTransfer ProtocolIE-ID ::= 305
id-MulticastSessionUpdateRequestTransfer ProtocolIE-ID ::= 306
id-MulticastGroupPagingAreaList ProtocolIE-ID ::= 307
id-MBS-SupportIndicator ProtocolIE-ID ::= 309
id-MBSSessionFailedtoSetupList ProtocolIE-ID ::= 310
id-MBSSessionFailedtoSetuporModifyList ProtocolIE-ID ::= 311
id-MBSSessionSetupResponseList ProtocolIE-ID ::= 312
id-MBSSessionSetuporModifyResponseList ProtocolIE-ID ::= 313
id-MBSSessionSetupFailureTransfer ProtocolIE-ID ::= 314
id-MBSSessionSetupRequestTransfer ProtocolIE-ID ::= 315
id-MBSSessionSetupResponseTransfer ProtocolIE-ID ::= 316
id-MBSSessionToReleaseList ProtocolIE-ID ::= 317
id-MBSSessionSetupRequestList ProtocolIE-ID ::= 318
id-MBSSessionSetuporModifyRequestList ProtocolIE-ID ::= 319
id-MBS-ActiveSessionInformation-SourcetoTargetList ProtocolIE-ID ::= 323
id-MBS-ActiveSessionInformation-TargettoSourceList ProtocolIE-ID ::= 324
id-OnboardingSupport ProtocolIE-ID ::= 325
id-TimeSyncAssistanceInfo ProtocolIE-ID ::= 326
id-SurvivalTime ProtocolIE-ID ::= 327
id-QMCConfigInfo ProtocolIE-ID ::= 328
id-QMCDeactivation ProtocolIE-ID ::= 329
id-PDUSessionPairID ProtocolIE-ID ::= 331
id-NR-PagingeDRXInformation ProtocolIE-ID ::= 332
id-RedCapIndication ProtocolIE-ID ::= 333
id-TargetNSSAIInformation ProtocolIE-ID ::= 334
id-UESliceMaximumBitRateList ProtocolIE-ID ::= 335
id-M4ReportAmount ProtocolIE-ID ::= 336
id-M5ReportAmount ProtocolIE-ID ::= 337
id-M6ReportAmount ProtocolIE-ID ::= 338
id-M7ReportAmount ProtocolIE-ID ::= 339
id-IncludeBeamMeasurementsIndication ProtocolIE-ID ::= 340
id-ExcessPacketDelayThresholdConfiguration ProtocolIE-ID ::= 341
id-PagingCause ProtocolIE-ID ::= 342
id-PagingCauseIndicationForVoiceService ProtocolIE-ID ::= 343
id-PEIPSassistanceInformation ProtocolIE-ID ::= 344
id-FiveG-ProSeAuthorized ProtocolIE-ID ::= 345
id-FiveG-ProSeUEPC5AggregateMaximumBitRate ProtocolIE-ID ::= 346
id-FiveG-ProSePC5QoSParameters ProtocolIE-ID ::= 347
id-MBSSessionModificationFailureTransfer ProtocolIE-ID ::= 348
id-MBSSessionModificationRequestTransfer ProtocolIE-ID ::= 349
id-MBSSessionModificationResponseTransfer ProtocolIE-ID ::= 350
id-MBS-QoSFlowToReleaseList ProtocolIE-ID ::= 351
id-MBS-SessionTNLInfo5GC ProtocolIE-ID ::= 352
id-TAINSAGSupportList ProtocolIE-ID ::= 353
id-SourceNodeTNLAddrInfo ProtocolIE-ID ::= 354
id-NGAPIESupportInformationRequestList ProtocolIE-ID ::= 355
id-NGAPIESupportInformationResponseList ProtocolIE-ID ::= 356
id-MBS-SessionFSAIDList ProtocolIE-ID ::= 357
id-MBSSessionReleaseResponseTransfer ProtocolIE-ID ::= 358
id-ManagementBasedMDTPLMNModificationList ProtocolIE-ID ::= 359
id-EarlyMeasurement ProtocolIE-ID ::= 360
id-BeamMeasurementsReportConfiguration ProtocolIE-ID ::= 361
id-HFCNode-ID-new ProtocolIE-ID ::= 362
id-GlobalCable-ID-new ProtocolIE-ID ::= 363
id-TargetHomeENB-ID ProtocolIE-ID ::= 364
id-HashedUEIdentityIndexValue ProtocolIE-ID ::= 365
id-ExtendedMobilityInformation ProtocolIE-ID ::= 366
id-NetworkControlledRepeaterAuthorized ProtocolIE-ID ::= 367
id-AdditionalCancelledlocationReportingReferenceIDList ProtocolIE-ID ::= 368
id-Selected-Target-SNPN-Identity ProtocolIE-ID ::= 369
id-EquivalentSNPNsList ProtocolIE-ID ::= 370
id-SelectedNID ProtocolIE-ID ::= 371
id-SupportedUETypeList ProtocolIE-ID ::= 372
id-AerialUEsubscriptionInformation ProtocolIE-ID ::= 373
id-NR-A2X-ServicesAuthorized ProtocolIE-ID ::= 374
id-LTE-A2X-ServicesAuthorized ProtocolIE-ID ::= 375
id-NR-A2X-UE-PC5-AggregateMaximumBitRate ProtocolIE-ID ::= 376
id-LTE-A2X-UE-PC5-AggregateMaximumBitRate ProtocolIE-ID ::= 377
id-A2X-PC5-QoS-Parameters ProtocolIE-ID ::= 378
id-FiveGProSeLayer2Multipath ProtocolIE-ID ::= 379
id-FiveGProSeLayer2UEtoUERelay ProtocolIE-ID ::= 380
id-FiveGProSeLayer2UEtoUERemote ProtocolIE-ID ::= 381
id-CandidateRelayUEInformationList ProtocolIE-ID ::= 382
id-SuccessfulPSCellChangeReportList ProtocolIE-ID ::= 383
id-IntersystemMobilityFailureforVoiceFallback ProtocolIE-ID ::= 384
id-TargetCellCRNTI ProtocolIE-ID ::= 385
id-TimeSinceFailure ProtocolIE-ID ::= 386
id-RANTimingSynchronisationStatusInfo ProtocolIE-ID ::= 387
id-RAN-TSSRequestType ProtocolIE-ID ::= 388
id-RAN-TSSScope ProtocolIE-ID ::= 389
id-ClockQualityReportingControlInfo ProtocolIE-ID ::= 390
id-RANfeedbacktype ProtocolIE-ID ::= 391
id-QoSFlowTSCList ProtocolIE-ID ::= 392
id-TSCTrafficCharacteristicsFeedback ProtocolIE-ID ::= 393
id-DownlinkTLContainer ProtocolIE-ID ::= 394
id-UplinkTLContainer ProtocolIE-ID ::= 395
id-ANPacketDelayBudgetUL ProtocolIE-ID ::= 396
id-QosFlowAdditionalInfoList ProtocolIE-ID ::= 397
id-AssistanceInformationQoE-Meas ProtocolIE-ID ::= 398
id-CommServiceType ProtocolIE-ID ::= 399
id-MobileIAB-Authorized ProtocolIE-ID ::= 400
id-MobileIAB-MTUserLocationInformation ProtocolIE-ID ::= 401
id-MobileIABNodeIndication ProtocolIE-ID ::= 402
id-NoPDUSessionIndication ProtocolIE-ID ::= 403
id-MobileIAB-Supported ProtocolIE-ID ::= 404
id-CN-MT-CommunicationHandling ProtocolIE-ID ::= 405
id-FiveGCAction ProtocolIE-ID ::= 406
id-PagingPolicyDifferentiation ProtocolIE-ID ::= 407
id-DL-Signalling ProtocolIE-ID ::= 408
id-PNI-NPN-AreaScopeofMDT ProtocolIE-ID ::= 409
id-PNI-NPNBasedMDT ProtocolIE-ID ::= 410
id-SNPN-CellBasedMDT ProtocolIE-ID ::= 411
id-SNPN-TAIBasedMDT ProtocolIE-ID ::= 412
id-SNPN-BasedMDT ProtocolIE-ID ::= 413
id-Partially-Allowed-NSSAI ProtocolIE-ID ::= 414
id-AssociatedSessionID ProtocolIE-ID ::= 415
id-MBS-AssistanceInformation ProtocolIE-ID ::= 416
id-BroadcastTransportFailureTransfer ProtocolIE-ID ::= 417
id-BroadcastTransportRequestTransfer ProtocolIE-ID ::= 418
id-BroadcastTransportResponseTransfer ProtocolIE-ID ::= 419
id-TimeBasedHandoverInformation ProtocolIE-ID ::= 420
id-DLDiscarding ProtocolIE-ID ::= 421
id-PDUsetQoSParameters ProtocolIE-ID ::= 422
id-PDUSetbasedHandlingIndicator ProtocolIE-ID ::= 423
id-N6JitterInformation ProtocolIE-ID ::= 424
id-ECNMarkingorCongestionInformationReportingRequest ProtocolIE-ID ::= 425
id-ECNMarkingorCongestionInformationReportingStatus ProtocolIE-ID ::= 426
id-ERedCapIndication ProtocolIE-ID ::= 427
id-XrDeviceWith2Rx ProtocolIE-ID ::= 428
id-UserPlaneErrorIndicator ProtocolIE-ID ::= 429
id-SLPositioningRangingServiceInfo ProtocolIE-ID ::= 430
id-PDUSessionListMTCommHReq ProtocolIE-ID ::= 431
id-MaximumDataBurstVolume ProtocolIE-ID ::= 432
id-MN-only-MDT-collection ProtocolIE-ID ::= 433
id-MBS-NGUFailureIndication ProtocolIE-ID ::= 434
id-UserPlaneFailureIndication ProtocolIE-ID ::= 435
id-UserPlaneFailureIndicationReport ProtocolIE-ID ::= 436
id-SourceSN-to-TargetSN-QMCInfo ProtocolIE-ID ::= 437
id-QoERVQoEReportingPaths ProtocolIE-ID ::= 438
id-UserLocationInformationN3IWF-without-PortNumber ProtocolIE-ID ::= 439
id-AUN3DeviceAccessInfo ProtocolIE-ID ::= 440
id-TAIMBSSupportList ProtocolIE-ID ::= 441
id-ExtendedBackupAMFName ProtocolIE-ID ::= 442
id-ExtendedOldAMF ProtocolIE-ID ::= 443
END

-- **************************************************************
--
-- Container definitions
--
-- **************************************************************
NGAP-Containers {
itu-t (0) identified-organization (4) etsi (0) mobileDomain (0)
ngran-Access (22) modules (3) ngap (1) version1 (1) ngap-Containers (5) }
DEFINITIONS AUTOMATIC TAGS ::=
BEGIN
-- **************************************************************
--
-- IE parameter types from other modules.
--
-- **************************************************************
IMPORTS
Criticality,
Presence,
PrivateIE-ID,
ProtocolExtensionID,
ProtocolIE-ID
FROM NGAP-CommonDataTypes
maxPrivateIEs,
maxProtocolExtensions,
maxProtocolIEs
FROM NGAP-Constants;
-- **************************************************************
--
-- Class Definition for Protocol IEs
--
-- **************************************************************
NGAP-PROTOCOL-IES ::= CLASS {
&id ProtocolIE-ID UNIQUE,
&criticality Criticality,
&Value,
&presence Presence
}
WITH SYNTAX {
ID &id
CRITICALITY &criticality
TYPE &Value
PRESENCE &presence
}
-- **************************************************************
--
-- Class Definition for Protocol IEs
--
-- **************************************************************
NGAP-PROTOCOL-IES-PAIR ::= CLASS {
&id ProtocolIE-ID UNIQUE,
&firstCriticality Criticality,
&FirstValue,
&secondCriticality Criticality,
&SecondValue,
&presence Presence
}
WITH SYNTAX {
ID &id
FIRST CRITICALITY &firstCriticality
FIRST TYPE &FirstValue
SECOND CRITICALITY &secondCriticality
SECOND TYPE &SecondValue
PRESENCE &presence
}
-- **************************************************************
--
-- Class Definition for Protocol Extensions
--
-- **************************************************************
NGAP-PROTOCOL-EXTENSION ::= CLASS {
&id ProtocolExtensionID UNIQUE,
&criticality Criticality,
&Extension,
&presence Presence
}
WITH SYNTAX {
ID &id
CRITICALITY &criticality
EXTENSION &Extension
PRESENCE &presence
}
-- **************************************************************
--
-- Class Definition for Private IEs
--
-- **************************************************************
NGAP-PRIVATE-IES ::= CLASS {
&id PrivateIE-ID,
&criticality Criticality,
&Value,
&presence Presence
}
WITH SYNTAX {
ID &id
CRITICALITY &criticality
TYPE &Value
PRESENCE &presence
}
-- **************************************************************
--
-- Container for Protocol IEs
--
-- **************************************************************
ProtocolIE-Container {NGAP-PROTOCOL-IES : IEsSetParam} ::=
SEQUENCE (SIZE (0..maxProtocolIEs)) OF
ProtocolIE-Field {{IEsSetParam}}
ProtocolIE-SingleContainer {NGAP-PROTOCOL-IES : IEsSetParam} ::=
ProtocolIE-Field {{IEsSetParam}}
ProtocolIE-Field {NGAP-PROTOCOL-IES : IEsSetParam} ::= SEQUENCE {
id NGAP-PROTOCOL-IES.&id ({IEsSetParam}),
criticality NGAP-PROTOCOL-IES.&criticality ({IEsSetParam}{@id}),
value NGAP-PROTOCOL-IES.&Value ({IEsSetParam}{@id})
}
-- **************************************************************
--
-- Container for Protocol IE Pairs
--
-- **************************************************************
ProtocolIE-ContainerPair {NGAP-PROTOCOL-IES-PAIR : IEsSetParam} ::=
SEQUENCE (SIZE (0..maxProtocolIEs)) OF
ProtocolIE-FieldPair {{IEsSetParam}}
ProtocolIE-FieldPair {NGAP-PROTOCOL-IES-PAIR : IEsSetParam} ::= SEQUENCE {
id NGAP-PROTOCOL-IES-PAIR.&id ({IEsSetParam}),
firstCriticality NGAP-PROTOCOL-IES-PAIR.&firstCriticality ({IEsSetParam}{@id}),
firstValue NGAP-PROTOCOL-IES-PAIR.&FirstValue ({IEsSetParam}{@id}),
secondCriticality NGAP-PROTOCOL-IES-PAIR.&secondCriticality ({IEsSetParam}{@id}),
secondValue NGAP-PROTOCOL-IES-PAIR.&SecondValue ({IEsSetParam}{@id})
}
-- **************************************************************
--
-- Container Lists for Protocol IE Containers
--
-- **************************************************************
ProtocolIE-ContainerList {INTEGER : lowerBound, INTEGER : upperBound, NGAP-PROTOCOL-IES : IEsSetParam} ::=
SEQUENCE (SIZE (lowerBound..upperBound)) OF
ProtocolIE-SingleContainer {{IEsSetParam}}
ProtocolIE-ContainerPairList {INTEGER : lowerBound, INTEGER : upperBound, NGAP-PROTOCOL-IES-PAIR : IEsSetParam} ::=
SEQUENCE (SIZE (lowerBound..upperBound)) OF
ProtocolIE-ContainerPair {{IEsSetParam}}
-- **************************************************************
--
-- Container for Protocol Extensions
--
-- **************************************************************
ProtocolExtensionContainer {NGAP-PROTOCOL-EXTENSION : ExtensionSetParam} ::=
SEQUENCE (SIZE (1..maxProtocolExtensions)) OF
ProtocolExtensionField {{ExtensionSetParam}}
ProtocolExtensionField {NGAP-PROTOCOL-EXTENSION : ExtensionSetParam} ::= SEQUENCE {
id NGAP-PROTOCOL-EXTENSION.&id ({ExtensionSetParam}),
criticality NGAP-PROTOCOL-EXTENSION.&criticality ({ExtensionSetParam}{@id}),
extensionValue NGAP-PROTOCOL-EXTENSION.&Extension ({ExtensionSetParam}{@id})
}
-- **************************************************************
--
-- Container for Private IEs
--
-- **************************************************************
PrivateIE-Container {NGAP-PRIVATE-IES : IEsSetParam } ::=
SEQUENCE (SIZE (1..maxPrivateIEs)) OF
PrivateIE-Field {{IEsSetParam}}
PrivateIE-Field {NGAP-PRIVATE-IES : IEsSetParam} ::= SEQUENCE {
id NGAP-PRIVATE-IES.&id ({IEsSetParam}),
criticality NGAP-PRIVATE-IES.&criticality ({IEsSetParam}{@id}),
value NGAP-PRIVATE-IES.&Value ({IEsSetParam}{@id})
}
END
